UIC-Object-Identifiers { iso(1) identified-organization(3) dod(6)
    internet(1) private(4) enterprise(1) uic(17218) fcb(1) modules(0) oids(0) }
    DEFINITIONS ::= BEGIN

EXPORTS ALL;

uicFcb OBJECT IDENTIFIER ::= { iso(1) identified-organization(3) dod(6)
    internet(1) private(4) enterprise(1) uic(17218) fcb(1) }

uicFcbAsn1Modules OBJECT IDENTIFIER ::= { uicFcb modules(0) }

bt4ptAsn1Modules OBJECT IDENTIFIER ::= { uicFcb bt4pt(2) }

uicPki OBJECT IDENTIFIER ::= { uicFcb pki(1) }

-- This module
objectIdentifiersModule OBJECT IDENTIFIER ::= { uicFcbAsn1Modules oids(0) }

-- UIC Barcode Header - version 1.0.0
uicBarcodeHeaderV1-0-0 OBJECT IDENTIFIER ::= { uicFcbAsn1Modules header(1) v1(1) 0 }

-- UIC Barcode Header - version 2.0.0
uicBarcodeHeaderV2-0-0 OBJECT IDENTIFIER ::= { uicFcbAsn1Modules header(1) v2(2) 0 }

-- UIC Barcode Header - version 2.0.1
uicBarcodeHeaderV2-0-1 OBJECT IDENTIFIER ::= { uicFcbAsn1Modules header(1) v2(2) 1 }

-- UIC Rail Ticket Data - version 1.3.0
uicRailTicketDataV1-3-0 OBJECT IDENTIFIER ::= { uicFcbAsn1Modules rtd(2) v1-3(1) 0 }

-- UIC Rail Ticket Data - version 1.3.1
uicRailTicketDataV1-3-1 OBJECT IDENTIFIER ::= { uicFcbAsn1Modules rtd(2) v1-3(1) 1 }

-- UIC Rail Ticket Data - version 1.3.3
uicRailTicketDataV1-3-3 OBJECT IDENTIFIER ::= { uicFcbAsn1Modules rtd(2) v1-3(1) 3 }

-- UIC Rail Ticket Data - version 1.3.4
uicRailTicketDataV1-3-4 OBJECT IDENTIFIER ::= { uicFcbAsn1Modules rtd(2) v1-3(1) 4 }

-- UIC Rail Ticket Data - version 1.3.5
uicRailTicketDataV1-3-5 OBJECT IDENTIFIER ::= { uicFcbAsn1Modules rtd(2) v1-3(1) 5 }

-- UIC Rail Ticket Data - version 2.0.0
uicRailTicketDataV2-0-0 OBJECT IDENTIFIER ::= { uicFcbAsn1Modules rtd(2) v2(2) 0 }

-- UIC Rail Ticket Data - version 2.0.1
uicRailTicketDataV2-0-1 OBJECT IDENTIFIER ::= { uicFcbAsn1Modules rtd(2) v2(2) 1 }

-- UIC Rail Ticket Data - version 2.0.2
uicRailTicketDataV2-0-2 OBJECT IDENTIFIER ::= { uicFcbAsn1Modules rtd(2) v2(2) 2 }

-- UIC Rail Ticket Data - version 2.0.3
uicRailTicketDataV2-0-3 OBJECT IDENTIFIER ::= { uicFcbAsn1Modules rtd(2) v2(2) 3 }

-- UIC Rail Ticket Data - version 3.0.0
uicRailTicketDataV3-0-0 OBJECT IDENTIFIER ::= { uicFcbAsn1Modules rtd(2) v3(3) 0 }

-- UIC Rail Ticket Data - version 3.0.1
uicRailTicketDataV3-0-1 OBJECT IDENTIFIER ::= { uicFcbAsn1Modules rtd(2) v3(3) 1 }

-- UIC Rail Ticket Data - version 3.0.2
uicRailTicketDataV3-0-2 OBJECT IDENTIFIER ::= { uicFcbAsn1Modules rtd(2) v3(3) 2 }

-- UIC Rail Ticket Data - version 3.0.3
uicRailTicketDataV3-0-3 OBJECT IDENTIFIER ::= { uicFcbAsn1Modules rtd(2) v3(3) 3 }

-- UIC Rail Ticket Data - version 3.0.4
uicRailTicketDataV3-0-4 OBJECT IDENTIFIER ::= { uicFcbAsn1Modules rtd(2) v3(3) 4 }

-- UIC Rail Ticket Data - version 3.0.5
uicRailTicketDataV3-0-5 OBJECT IDENTIFIER ::= { uicFcbAsn1Modules rtd(2) v3(3) 5 }

-- UIC Rail Ticket Data - version 3.0.6
uicRailTicketDataV3-0-6 OBJECT IDENTIFIER ::= { uicFcbAsn1Modules rtd(2) v3(3) 6 }

-- UIC Rail Ticket Data - version 3.0.7
uicRailTicketDataV3-0-7 OBJECT IDENTIFIER ::= { uicFcbAsn1Modules rtd(2) v3(3) 7 }

-- FCB Dynamic Content Data - version 1.0.0
uicDynamicContentDataV1-0-0 OBJECT IDENTIFIER ::= { uicFcbAsn1Modules dcd(3) v1(1) 0 }

-- FCB Dynamic Content Data - version 1.0.1
uicDynamicContentDataV1-0-1 OBJECT IDENTIFIER ::= { uicFcbAsn1Modules dcd(3) v1(1) 1 }

-- FCB Dynamic Content Data - version 1.0.2
uicDynamicContentDataV1-0-2 OBJECT IDENTIFIER ::= { uicFcbAsn1Modules dcd(3) v1(1) 2 }

-- FCB Dynamic Content Data - version 1.0.3
uicDynamicContentDataV1-0-3 OBJECT IDENTIFIER ::= { uicFcbAsn1Modules dcd(3) v1(1) 3 }

-- FCB Dynamic Content Data - version 1.0.4
uicDynamicContentDataV1-0-4 OBJECT IDENTIFIER ::= { uicFcbAsn1Modules dcd(3) v1(1) 4 }

-- FCB Dynamic Content Data - version 1.0.5
uicDynamicContentDataV1-0-5 OBJECT IDENTIFIER ::= { uicFcbAsn1Modules dcd(3) v1(1) 5 }

-- BT4PT General cross-module elements - version 1.0, currently a draft
bt4ptGeneralElementsV1-0 OBJECT IDENTIFIER ::= { bt4ptAsn1Modules general(1) v1(1) 0 }

-- BT4PT Envelope - version 1.0, currently a draft
bt4ptEnvelopeV1-0 OBJECT IDENTIFIER ::= { bt4ptAsn1Modules envelope(2) v1(1) 0 }

-- BT4PT Multi-Modal Ticket Data - version 1.0, currently a draft
bt4ptMultiModalTicketDataV1-0 OBJECT IDENTIFIER ::= { bt4ptAsn1Modules mmtd(3) v1(1) 0 }

-- BT4PT Dynamic Content Data - version 1.0, currently a draft
bt4ptDynamicContentDataV1-0 OBJECT IDENTIFIER ::= { bt4ptAsn1Modules dcd(4) v1(1) 0 }

-- BT4PT Fixed Point Data - version 1.0, currently a draft
bt4ptFixedPointDataV1-0 OBJECT IDENTIFIER ::= { bt4ptAsn1Modules fpd(5) v1(1) 0 }

-- BT4PT HSM Trace Data - version 1.0, currently a draft
bt4ptHSMTraceV1-0 OBJECT IDENTIFIER ::= { bt4ptAsn1Modules hsm(6) v1(1) 0 }

-- BT4PT Certificates - version 1.0, currently a draft
bt4ptCertificatesV1-0 OBJECT IDENTIFIER ::= { bt4ptAsn1Modules certificates(7) v1(1) 0 }

-- BT4PT Metadata - version 1.0, currently a draft
bt4ptMetadataV1-0 OBJECT IDENTIFIER ::= { bt4ptAsn1Modules metadata(8) v1(1) 0 }

-- BT4PT Encrypted Data - version 1.0, currently a draft
bt4ptEncryptedDataV1-0 OBJECT IDENTIFIER ::= { bt4ptAsn1Modules encryptedData(11) v1(1) 0 }

-- BT4PT Luggage Tag - version 1.0, currently a draft
bt4ptLuggageTagV1-0 OBJECT IDENTIFIER ::= { bt4ptAsn1Modules luggageTag(12) v1(1) 0 }

-- BT4PT Presentment Applet - version 1.0, currently a draft
bt4ptPresentmentAppletModuleV1-0 OBJECT IDENTIFIER ::= { bt4ptAsn1Modules presentmentApplet(13) v1(1) 0 }


bt4ptApplets OBJECT IDENTIFIER ::= { uicFcb bt4ptApplets(3) }

-- BT4PT Presentment Applet - general OID
bt4ptPresentmentApplet OBJECT IDENTIFIER ::= { bt4ptApplets presentmentApplet(1) }

-- BT4PT Presentment Applet - version 1.0
bt4ptPresentmentAppletV1 OBJECT IDENTIFIER ::= { bt4ptPresentmentApplet v1(1) }

-- BT4PT HSM Applet
bt4ptHSMAppletV1 OBJECT IDENTIFIER ::= { bt4ptApplets hsmApplet(2) v1(1) }

END
