BT4PT-GeneralElementsV1-0 {
    iso(1) identified-organization(3) dod(6) internet(1) private(4) enterprise(1) uic(17218) fcb(1) bt4pt(2) general(1) v1(1) 0
} DEFINITIONS ::= BEGIN

EXPORTS ALL;

/**
* This data structure is used throughout this standard when encoding as identifier for some object, event, entity, etc.
* The exact values and their meaning are defined by the context in which the identifier is used.
*
* For the purposes of this structure, an identifier is *integer-compatible* if its value consists exclusively of
* decimal digits (U+0030 to U+0039), and either consists of the single digit 0, or does not begin with the digit 0.
* An identifier containing leading zeroes **SHALL NOT** be considered integer-compatible, as those zeroes may be
* significant to the identity of the identifier.
*
*
* When encoding an identifier, an implementation of this standard SHALL:
* 1. encode using the `idNum` variant, if the value to be encoded is integer-compatible;
* 2. encode using the `idStr` variant, if the value to be encoded is a string consisting only of characters
*    representable by the ASN.1 `VisibleString` type, but is not integer-compatible; or
* 3. encode using the `idOct` variant, if the value to be encoded is binary, or cannot be represented using either of the above variants.
*
* The `idStr` variant **MAY** contain punctuation, spaces, and other characters permitted by the `VisibleString` type.
* Such characters **SHALL** be preserved in the canonical textual representation.
*
* Two values **SHALL** be considered equal if, and only if, their canonical textual representations, are identical.
* The variant used **SHALL NOT** otherwise affect equality. That is, `1234` encoded as an `idNum` is the exact same
* logical value as the string `"1234" encoded as idStr, and the same logical value as the binary string `'31323334'H`.
* However, the string `"01234"` is a distinct identifier from ``1234"`, irrespective of the variant used to encode either value.
*/
GenericId ::= [APPLICATION 13] CHOICE {
    /**
    * To be used for numeric IDs.
    * Negative integers **SHALL NOT** be used as identifiers.
    */
    idNum   INTEGER (0..MAX),
    /**
    * To be used for alphanumeric IDs.
    */
    idStr   VisibleString,
    /**
    * To be used for binary IDs, such as UUIDs.
    */
    idOct   OCTET STRING
}

/**
* This data structure is used throughout this standard to specify which dataset an identifier references.
* This avoids possible confusions between, e.g. station identifier 1312 being assigned to different stations
* in different national schemes.
*/
CodeTable ::= SEQUENCE {
    /**
    * This field defines which organisation or entity controls or otherwise administers the dataset to which
    * an identifier refers.
    */
    owner CHOICE {
        /**
        * Identifiers are defined by the issuer. When decoding this variant **SHALL** be dereferenced to
        * the contextually relevant {@link CompanyCode}. When encoding, this variant **SHALL** be preferred over the variant
        * `Company` where possible, to save encoding space.
        */
        issuer          [1] NULL,
        /**
        * Identifiers are defined by the product owner. When decoding this variant **SHALL** be dereferenced to
        * the contextually relevant {@link CompanyCode}. When encoding, this variant **SHALL** be preferred over the variant
        * `Company` where possible, to save encoding space.
        */
        productOwner    [2] NULL,
        /**
        * Identifiers are defined by the carrier. When decoding this variant **SHALL** be dereferenced to
        * the contextually relevant {@link CompanyCode}. When encoding, this variant **SHALL** be preferred over the variant
        * `company` where possible, to save encoding space. If there are multiple possible contextually relevant
        * carriers, this variant **SHALL NOT** be used, as its meaning is then ambiguous.
        */
        carrier         [3] NULL,
        /**
        * Identifiers are defined by entity responsible for the relevant 'Concerned Area'.
        * When decoding this variant **SHALL** be dereferenced to the contextually relevant {@link NUTSArea}.
        * If there are multiple possible contextually relevant concerned areas, this variant **SHALL NOT** be used,
        * as its meaning is then ambiguous.
        *
        * This variant **SHALL NOT** be used for an identifier before it is registered with [insert registration authority].
        * The registration authority will make a determination on whether the suggested dataset can accurately be considered
        * a regional dataset, covering all possible identifiers in a given context for multi-modality in that area.
        */
        area            [4] NULL,
        /**
        * Identifiers are defined a national authority for a country. This field contains the [](cite:iso3166-1) numeric code
        * of that country.
        *
        * This variant **SHALL NOT** be used for an identifier before it is registered with [insert registration authority].
        * The registration authority will make a determination on whether the suggested dataset can accurately be considered
        * a national dataset, covering all possible identifiers in a given context for multi-modality in that country.
        */
        national        [5] INTEGER (0..999),
        /**
        * Identifiers are defined by the given company.
        */
        company         CompanyCode
    },
    /**
    * This field is used in case of multiple datasets being maintained by the same entity for the same
    * purpose, to differentiate between them. Examples could include BeispielBahn having two different possible
    * identifiers for a station.
    *
    * **Note:** this field is not used to differentiate between different datasets used by the same entity for
    * different purposes. That is, the dataset of, e.g., BeispielBahn for areas and for stations may both be given
    * version 0. It is evident from the context in which this structure is used, to which dataset the identifier refers.
    */
    version INTEGER (0..255) DEFAULT 0
}

CODE-TABLE-IDENTIFIER ::= CLASS {
    &table CodeTable UNIQUE
}

GenericCode{IdType, CODE-TABLE-IDENTIFIER: TableSet} ::= [APPLICATION 5] SEQUENCE {
    /**
    * Denotes to which dataset the identifier references.
    */
    codeTable CODE-TABLE-IDENTIFIER.&table({TableSet}),
    /**
    * The identifier, as defined by the dataset referenced in `codeTable`.
    */
    id IdType
}

/**
* This data structure is used throughout this standard when referring to the various organisations or authorities
* responsible for the various aspects of ticketing and carriage of passengers. In Transmodel terms it identifies a
* TRANSPORT ORGANIZATION per [](cite:en12896-1 "5.6.8").
*/
CompanyCode ::= [APPLICATION 2] CHOICE {
    /**
    * For companies within the EU this field **SHALL** be their ERA assigned Organisation Code per [](cite:cid2018-1614 "II.3.2.4"),
    *  as available from [teleref.era.europa.eu](https://teleref.era.europa.eu).
    * For others this field **SHALL** be their UIC assigned RICS, as available
    *  from [uic.org/support-activities/it/rics](https://uic.org/support-activities/it/rics).
    */
    orgCode     VisibleString (SIZE (4) ^ FROM ("A".."Z"|"0".."9")),

    /**
    * This variant is to be used when a company does not have an ERA Organisation Code nor a RICS. It **SHALL NOT**
    * be used when a company has an ERA Org Code or RICS assigned to it, except where the situation requires
    * identifying the company within the context of a local coding system.
    */
	otherCode   SEQUENCE {
	    /**
		* The company identifier format is constructed according to one of the following options:
		* 1. The literal character `+` (`U+002B`, PLUS SIGN), concatenated with a 2-character uppercase [](cite:iso3166-1)
		*    country code, concatenated with a string chosen by the national standards body of that country.
		* 2. The literal character `_` (`U+005F`, LOW LINE), concatenated with a 4-character ERA Organisation Code per
		*    [](cite:cid2018-1614 "II.3.2.4") or RICS, concatenated with a string chosen by that company.
		* 3. The literal character `*` (`U+002A`, ASTERISK), concatenated with privately chosen string. **Note:** this variant has no guarantees
		*    of avoiding clashes in assignment, and **SHOULD NOT** be used unless no other option is available.
		*    If an organisation has a ERA Organisation Code or a RICS, this variant **SHALL NOT** be used.
		* 4. Any other string, as assigned in this standard. Unregistered values of this variant **SHALL NOT** be used.
		*
        * The 1st and 2nd variant **SHOULD** be registered _before_ their first use.
        * The 4th variant **SHALL** be registered _before_ its first use.
        * Registrations **SHALL** be made with [insert registration authority].
		*/
		format      COMPANY-CODE-FORMAT.&id({CompanyCodeFormats}),
		/**
		* The meaning of this field is defined by value of `format`.
		*/
		code        VisibleString (SIZE(1..8,...))
	}
}

COMPANY-CODE-FORMAT ::= CLASS {
    &id VisibleString (SIZE(1..8) ^ (ALL EXCEPT ("!I" | "!C" | "!P"))) UNIQUE
}

/**
* When a company does not have an ERA Organisation Code per [](cite:cid2018-1614 "II.3.2.4"), an entry from this list
* **SHALL** be used to signify which alternative dataset is being used to identify the company.
*
* The entries in this list are managed by [insert registration authority].
*/
CompanyCodeFormats COMPANY-CODE-FORMAT ::= {
    /**
    * Verband Deutscher Verkehrsunternehmen Organisation ID.
    */
    { &id "+DEVDV" } |
    /**
    * Traveline National Operator Code.
    */
    { &id "+GBNOC" } |
    /**
    * Swiss Business Organisation Identification.
    * SBOIDs **SHALL** be encoded omitting the `ch:1:sboid:` prefix.
    */
    { &id "+CHSBOID" },
    ...
}

/**
* This data structure is used in Data Authorisation constraints to restrict which companies a field identifying a
* company is permitted to contain.
*
* A company is permitted by a `CompanyConstraint` if either:
* 1. `securityProvider` is `TRUE`, and the company under test is the Security Provider of the envelope.
* 2. `permitted` is present, and the company under test is equal to one of its entries.
*
* Otherwise, the company under test is not permitted.
*/
CompanyConstraint ::= SEQUENCE {
    /**
    * Whether the Security Provider of the envelope is permitted.
    */
    securityProvider    BOOLEAN,
    /**
    * The companies, other than the Security Provider, that are permitted. If absent, no company other than the 
    * Security Provider is permitted.
    */
    permitted           SEQUENCE (SIZE(1..32)) OF CompanyCode OPTIONAL
}

/**
* This data structure is used throughout this standard for the encoding of text which is intended to be displayed to
* a human being. This standard utilises the Unicode character set for such purposes.
*
* Implementations of this standard **SHALL** be compliant to [](cite:din91379), with regards to processing text in this structure.
* That is, they are able to handle (store, transfer, recall, and represent) all characters as specified in [](cite:din91379) without error.
*/
UnicodeText ::= [APPLICATION 4] SEQUENCE {
    /**
    * The textual data, encoded according to the [Standard Compression Scheme for Unicode (SCSU)](cite:uts6).
    * All Unicode text, before being fed into the SCSU compressor, **SHALL** be in [Normalisation Form C](cite:uax6).
    *
    * For encoders than only ever output Latin-1 (per [](cite:iso8859-1) between `U+0020` and `U+00FF`, no special
    * handling is required to generate SCSU data, the Latin-1 encoding is already valid SCSU.
    * All decoders **SHALL** be able to handle the full SCSU specification when reading and parsing data.
    *
    * If you are unsure which implementation to use, the [International Components for Unicode](https://icu.unicode.org/)
    *  is the recommended implementation of SCSU, although it is by no means required.
    */
    text        OCTET STRING,
    /**
    * The [IANA language subtag](https://www.iana.org/assignments/language-subtag-registry/language-subtag-registry) (per [](cite:bcp47)) of the text.
    */
    language    VisibleString (SIZE(2) ^ FROM ("a".."z"))
}

/**
* This data structure is used fo the encoding of a person's name.
* The encoding considerations and rules of {@link UnicodeText} apply equally to this structure.
*
* When comparing names with identity documents, or when a Latinized representation of a name is required,
*   the system **SHALL** transliterate according to [](cite:icao9303-3), specifically sections 4.6 and 6.
* The text stored in the ticket **SHOULD** be in its original script, with transliteration performed by the reading device.
* The reading device **SHOULD** show both the original script, and the Latinized form.
*
* The `language` field, if present, **SHALL** be used to select to correct Latinization of Cyrillic characters.
* The relevant languages for special considerations in ICAO 9303 Latinization are:
* - `be`: Belarusian
* - `bg`: Bulgarian
* - `uk`: Ukrainian
* - `mk`: Macedonian
* - `sr`: Serbian
*
* The `language` field **MAY** also be used to influence other transliterations, e.g. the different handling of diaereses by language.
*
* All 3 name parts are encoded with SCSU compression (as per {@link UnicodeText}).
* The language tag applies to all 3 name parts.
* That is, the name parts are to be construed as 3 UnicodeText SEQUENCEs with the same language tag set.
*/
Name ::= SEQUENCE {
    /**
    * The forename(s) of the person.
    */
    forename        OCTET STRING                                OPTIONAL,
    /**
    * The middle name(s) of the person, if applicable.
    */
    middleName      OCTET STRING                                OPTIONAL,
    /**
    * The surname(s) of the person.
    * In the case of a mononym, this field **SHALL** contain the name, and the `forename` and `middleName` fields
    * **SHALL** be unset.
    */
    surname         OCTET STRING                                OPTIONAL,
    /**
    * The [IANA language subtag](https://www.iana.org/assignments/language-subtag-registry/language-subtag-registry) (per [](cite:bcp47)) of the names' language.
    */
    language        VisibleString (SIZE(2) ^ FROM ("a".."z"))   OPTIONAL
}

/**
* This data structure is used to identify a station, stop, or other such boarding/alighting point.
* In Transmodel terms, it identifies a STOP PLACE per [](cite:en12896-1 "5.4.3").
*/
Station ::= [APPLICATION 6] SEQUENCE {
    /**
    * Contains the identifier used for the station.
    */
    station     CHOICE {
        /**
        * Identification of the station by its ERA assigned Primary Location Code per [](cite:cir2026-253 "9.3.b"), as available from [teleref.era.europa.eu](https://teleref.era.europa.eu).
        * This variant **SHALL** be used when a station has such a code assigned.
        *
        * **Note:** a PLC is _not_ equivalent to a UIC station ID, an IBNR (Internationale/Interne Bahnhofsnummer),
        * nor a MERITS reservation code. Although there may be some equivalence between these numbers in certain
        * countries, these are identifiers for separate systems and are _not_ interchangeable.
        */
        eraPlc      SEQUENCE {
            /**
            * The [](cite:iso3166-1) numeric code of the country of the PLC.
            */
            country         INTEGER (0..999),
            /**
            * The national part of the PLC.
            */
            locationCode    INTEGER (1..99999)
        },
        /**
        * If a station does not have an ERA Primary Location Code assigned, this variant is to be used.
        * This variant **SHALL NOT** be used when a station has as assigned ERA Primary Location Code.
        */
        generic     GenericCode{GenericId, {StationCodeTables}}
    },
    /**
    * This field **MAY** be used to provide a human-readable name for the station, to assist in cases where the
    * device reading a ticket does not have the appropriate dataset to dereference the identifier encoded in `station`.
    *
    * This field **SHALL NOT** be processed automatically, including, but not limited to, string matching the
    * provided station to a dataset. It **SHALL** only be used for display to a human being.
    */
    stationName UnicodeText OPTIONAL
}

/**
* When a `Station` does not have an ERA Primary Location Code, an entry from this list **SHALL** be used to signify
* which alternative dataset is being used to identify the station.
*
* The entries in this list are managed by [insert registration authority].
*/
StationCodeTables CODE-TABLE-IDENTIFIER ::= {
    /**
    * A UK National Location Code.
    * NLCs **SHALL** be encoded as `idStr`.
    * This code table **SHALL NOT** be used except when an NLC contains letters, and thus can't be turned into an ERA PLC.
    */
    {&table {
        owner company : orgCode : "1170",
        version 0
    }} |
    /**
    * A UK [NaPTAN](https://beta-naptan.dft.gov.uk/) Code. NaPTAN IDs **SHALL** be encoded as `idStr`.
    */
    {&table {
        owner national : 826,
        version 0
    }} |
    /**
    * A ZHV Deutschlandweite Haltestellen-ID.
    * DHIDs **SHALL** be encoded as `idStr`, omitting the `de:` prefix.
    */
    {&table {
        owner national : 276,
        version 0
    }} |
    /**
    * A Swiss LOcation IDentification.
    * SLOIDs **SHALL** be encoded as `idStr`, omitting the `ch:1:sloid:` prefix.
    */
    {&table {
        owner national : 756,
        version 0
    }},
    ...
}

StationSet ::= [APPLICATION 7] SEQUENCE {
    set CHOICE {
        /**
        * Where a station group is defined a number of stations grouped together with a primary station.
        */
        groupPrimary    [1] Station,
        /**
        * Explicitly listing all stations in a group.
        */
        list            [2] SEQUENCE OF Station
    },
    setNameUTF8 UnicodeText OPTIONAL
}

/**
* This data structure is used to identify a service line, for which many services may run in a day.
* In Transmodel terms, it identifies a LINE [](cite:en12896-1 "5.3.7.4").
*/
LineId ::= [APPLICATION 8] CHOICE {
    /**
    * An end-user-visible (i.e. published in timetables) identifier for the line.
    */
    publicIdentifier    SEQUENCE {
        /**
        * The identifier of the line; e.g. "RE1", "S1", etc.
        */
        id      VisibleString (FROM ("A".."Z"|"0".."9")),
        /**
        * The carrier that operates the line.
        */
        carrier CompanyCode
    },
    /**
    * A non-end-user-visible identifier for the line.
    */
    generic             GenericCode{GenericId, {LineIdCodeTables}}
}

/**
* When a {@link LineId} is being identified with a non-end-user-visible identifier, an entry from this list **SHALL** be
* used to signify which dataset is being used to identify the line.
*
* The entries in this list are managed by [insert registration authority].
*/
LineIdCodeTables CODE-TABLE-IDENTIFIER ::= {
    /**
    * VDV 431-2 Line ID.
    * Line IDs **SHALL** be encoded as `idStr`, omitting the `de:` prefix.
    */
    {&table {
        owner national : 276,
        version 0
    }} |
    /**
    * Swiss LiNe IDentification.
    * SLNIDs **SHALL** be encoded as `idStr`, omitting the `ch:1:slnid:` prefix.
    */
    {&table {
        owner national : 756,
        version 0
    }},
    ...
}

/**
* This data structure is used to identify a singular transport service, ideally unique within a day.
* In Transmodel terms, it identifies a SERVICE JOURNEY [](cite:en12896-1 "5.3.2").
*/
TransportId ::= [APPLICATION 9] CHOICE {
    /**
    * An end-user-visible (i.e. published in timetables) identifier for the service.
    */
    publicIdentifier    SEQUENCE {
        /**
        * The identifier of the service; e.g. "ICE107", etc.
        */
        id      VisibleString (FROM ("A".."Z"|"0".."9")),
        /**
        * The carrier that operates the service.
        *
        * In cases of railway services, this field **SHALL** contain the Lead Railway Undertaking for the service per [](cite:cir2026-253 "13").
        */
        carrier CompanyCode
    },
    /**
    * A non-end-user-visible identifier for the transport.
    */
    generic             GenericCode{GenericId, {TransportIdCodeTables}}
}

/**
* When a {@link TransportId} is being identified with a non-end-user-visible identifier, an entry from this list
* **SHALL** be used to signify which dataset is being used to identify the service.
*
* The entries in this list are managed by [insert registration authority].
*/
TransportIdCodeTables CODE-TABLE-IDENTIFIER ::= {
    /**
    * VDV 431-2 Journey ID.
    * Journey IDs **SHALL** be encoded as `idStr`, omitting the `de:` prefix.
    */
    {&table {
        owner national : 276,
        version 0
    }} |
    /**
    * RDG UID. These **SHALL** be encoded as `idStr`.
    */
    {&table {
        owner company : orgCode : "1170",
        version 0
    }} |
    /**
    * Swiss JourneY IDentification.
    * SJYIDs **SHALL** be encoded as `idStr`, omitting the `ch:1:sjyid:` prefix.
    */
    {&table {
        owner national : 756,
        version 0
    }},
    ...
}

/**
* This structure identifies a geographic area defined under the Nomenclature of Territorial Units for
* Statistics (per [](cite:reg2003-1059)), or a compatible system for those countries outside of the NUTS system.
*
* Divisions all the way down to the Local Administrative Unit are permitted.
* LAUs must be appended to their NUTS3 code, e.g. `270942` for Emmendingen, Stadt is coded with the subdivision `133270942`.
* Functional Administrative Unit codes are not permitted.
*
* NUTS codes are only defined for members of the EU, the EFTA, and EU candidate countries.
* For those countries outside the NUTS system:
* - the UK maintains a compatible system since Brexit called the [International Territorial Level](https://www.ons.gov.uk/aboutus/whatwedo/programmesandprojects/europeancitystatistics);
* - otherwise, use the the [OECD Territorial Region Codes](http://oe.cd/geostats).
* - if none of the above applies for a country, a choice of suitable system **SHALL** be defined by a future revision
*    of this specification. Users of this specification **SHALL NOT** make their own determination of a compatible system.
*    Countries without a suitable system **MAY** be identified only with the omission of the `subdivision` field.
*/
NUTSArea ::= [APPLICATION 10] SEQUENCE {
    /**
    * The ISO 3166-1 numeric code of the country of the area.
    */
    country         INTEGER (0..999),
    /**
    * The NUTS code, without the country-code prefix.
    * If this field is unset, the structure refers to the entire country.
    */
    subdivision     VisibleString (FROM ("A".."Z"|"0".."9")) OPTIONAL
}

/**
* This structure identifies one or more areas of geographic validity, e.g. fare zones.
*/
AreaSet ::= [APPLICATION 11] CHOICE {
    /**
    * A list of European NUTS codes, or compatible.
    * This variant **SHOULD** be used over the `generic` variant where possible.
    */
    nuts    [1] SET OF NUTSArea,
    /**
    * A list of area identifiers defined in terms of an identified code list.
    *
    * The same rules of equivalence under equality comparisons that apply to {@link GenericId} apply here as well,
    * except to the `idBit` variant.
    * Lists which contain the same values but in a different order are also equivalent.
    */
    generic [2] GenericCode{CHOICE {
        /**
        * To be used for numeric IDs.
        */
        idNum    [1] SET OF INTEGER (0..MAX),
        /**
        * To be used for alphanumeric IDs.
        */
        idStr    [2] SET OF VisibleString,
        /**
        * To be used for binary IDs.
        */
        idOct    [3] SET OF OCTET STRING,
        /**
        * An encoding in which each area is encoded as one bit.
        * That is, when a bit is set the area/zone is included in the `AreaSet`,
        * when it is not set the area/zone is excluded from the `AreaSet`.
        *
        * For example, where bit n (with bit 0 being right-most bit) encodes zone n+1, the value
        * `'10101110010'B` encodes zones 2, 5, 6, 7, 9 and 11.
        */
        idBit    [4] BIT STRING
    }, {AreaCodeTables}}
}

/**
* When an {@link AreaSet} is being identified with a non-NUTS identifier, an entry from this list
* **SHALL** be used to signify which dataset is being used to identify the area.
*
* The entries in this list are managed by [insert registration authority].
*/
AreaCodeTables CODE-TABLE-IDENTIFIER ::= {
    /**
    * Danish Rejsekort zone.
    * Rejsekort zone IDs **SHALL** be encoded as `idNum`.
    */
    {&table {
        owner national : 208,
        version 0
    }} |
    /**
    * German _Amtlicher Regionalschlüssel_ (ARS).
    * ARS IDs **SHALL** be encoded as `idStr` and contain only decimal digits.
    * Values **SHALL** have one of the following lengths:
    * - length 2 (00-99): _Land_ (Federal State)
    * - length 3 (00 0-99 9): _Regierungsbezirk_ (Administrative Area)
    * - length 5 (00 0 00-99 9 99): _Kreis_ (County)
    * - length 9 (00 0 00 0000-99 9 99 9999): _Gemeindeverband_ (Municipal Association)
    * - length 12 (00 0 00 0000 000-99 9 99 9999 9999): _Gemeinde_ (Municipality)
    */
    {&table {
        owner national : 276,
        version 0
    }},
    ...
}

/**
* This data structure is used to locate seats/places within a coach/carriage. It is used, for example, when encoding
* a seat reservation barcode. The data **SHALL** be construed in accordance with [](cite:tel-tsi-b5).
*/
CoachPlaces ::= SEQUENCE {
    /**
    * A human readable number/letter/identifier of the coach/carriage within one transport service.
    */
    coach               [1] VisibleString           OPTIONAL,
    /**
    * Individual places within the above coach.
    */
    placeNumber         [2] SEQUENCE OF PlaceNumber OPTIONAL,
    /**
    * This field **MAY** be used to provide more details about the seats/places, in accordance with [](cite:tel-tsi-b5).
    */
    details             [3] PlaceDetails            OPTIONAL,
    /**
    * This field **MAY** contain a human-readable description of the place, if it cannot be represented using any of
    * the other above fields.
    */
    placeDescription    [4] UnicodeText             OPTIONAL
}

/**
* This data structure identifies an individual seat/place within a single coach/carriage.
*/
PlaceNumber ::= CHOICE {
    /**
    * This variant **SHALL** be used when the seat/place identifier is a number.
    */
    placeNum      INTEGER (1..999),
    /**
    * This variant **SHALL** be used when the seat/place identifier is not a number.
    */
    placeIA5      VisibleString
}

/**
* This data structure provides additional details about a seat/place/compartment, in accordance with [](cite:tel-tsi-b5).
*/
PlaceDetails ::= SEQUENCE {
    /**
    * This field **SHALL** contain a value per [](cite:tel-tsi-b5 "51.1").
    */
    coachType       INTEGER (0..99),
    /**
    * This field **SHALL** contain a value per [](cite:tel-tsi-b5 "51.2").
    */
    compartmentType INTEGER (0..99),
    /**
    * This field **SHALL** contain a value per [](cite:tel-tsi-b5 "51.3").
    */
    specialOffers   INTEGER (0..99),
    /**
    * This field **MAY** contain a human-readable description of any details about the seat/place that can't be
    * represented with the above fields.
    */
    description     UnicodeText     OPTIONAL
}

/**
* This data structure is used to represent points on the globe. It **SHALL** contain a latitude and longitude as
* measurements compatible with [](cite:wgs84), as used by GPS navigation satellites.
*/
GeoCoordinate ::= SEQUENCE {
    /**
    * The exact point being referenced if no `accuracy` is given, or the centre of the possible circle of positions if
    * `accuracy` is given.
    */
    position            GeoPosition,
    /**
    * If known, the accuracy of the measurement given in `position`.
    * If the degrees of accuracy is more than 0.1 degrees, this value **SHALL** not be provided.
    *
    * At a latitude of exactly 90° north or south, the accuracy **SHALL** be considered greater than 0.1 degrees,
    * and the GeoAccuracy field **SHALL** be omitted.
    */
    accuracy            GeoAccuracy OPTIONAL
}

/**
* This enumeration is used to describe the accuracy of a geographic position measurement, in terms of variance range
* from the given centre coördinate.
*
* To convert between meters of accuracy and degrees of accuracy, an implementation **SHALL**:
* 1. Let the earth's circumference be 40,075,016.7 meters, per [](cite:wgs84).
* 2. Let the meters per degree at a given latitude be the cosine of the latitude in radians, times the earth's circumference, divided by 360.
*    That is, the following formula: `M = cos(latitude * π / 180) * 40075016.7 / 360`.
* 3. The degrees of accuracy is the meters of accuracy divided by the meters per degree at the latitude.
*    That is, the following formula `A = meters of accuracy / M`.
*/
GeoAccuracy ::= ENUMERATED {
    /**
    * The value `A` is less than or equal to 0.0001 degrees.
    */
    tenthMilliDegree    (0),
    /**
    * The value `A` is less than or equal to 0.001 degrees.
    */
    milliDegree         (1),
    /**
    *The value `A` is less than or equal to 0.01 degrees.
    */
    centiDegree         (2),
    /**
    * The value `A` is less than or equal to 0.1 degrees.
    */
    deciDegree          (3)
}

/**
* This data structure describes an exact point on the earth's surface.
*
* Implementations **SHALL** take into account the useful number of significant places (e.g. based upon the measurement
* accuracy) in a coördinate, and **SHALL** select the smallest variant suitable (i.e. least number of decimal places
* represented), to provide an encoding of the position in as few bits as possible.
*/
GeoPosition ::= CHOICE {
    /**
    * This variant is used to represent coördinates down to the 4th decimal place (0.0001 degrees).
    */
    tenthMilliDegree [1] SEQUENCE {
        /**
        * This field **SHALL** be populated with the degrees of longitude, multiplied by 10,000.
        */
        longitude INTEGER (-1800000..1800000),
        /**
        * This field **SHALL** be populated with the degrees of latitude, multiplied by 10,000.
        */
        latitude  INTEGER (-900000..900000)
    },
    /**
    * This variant is used to represent coördinates down to the 3rd decimal place (0.001 degrees).
    */
    milliDegree [2] SEQUENCE {
        /**
        * This field **SHALL** be populated with the degrees of longitude, multiplied by 1000.
        */
        longitude INTEGER (-180000..180000),
        /**
        * This field **SHALL** be populated with the degrees of latitude, multiplied by 1000.
        */
        latitude  INTEGER (-90000..90000)
    },
    /**
    * This variant is used to represent coördinates down to the 2nd decimal place (0.01 degrees).
    */
    centiDegree [3] SEQUENCE {
        /**
        * This field **SHALL** be populated with the degrees of longitude, multiplied by 100.
        */
        longitude INTEGER (-18000..18000),
        /**
        * This field **SHALL** be populated with the degrees of latitude, multiplied by 100.
        */
        latitude  INTEGER (-9000..9000)
    },
    /**
    * This variant is used to represent coördinates down to the 1st decimal place (0.1 degrees).
    */
    deciDegree [4] SEQUENCE {
        /**
        * This field **SHALL** be populated with the degrees of longitude, multiplied by 10.
        */
        longitude INTEGER (-1800..1800),
        /**
        * This field **SHALL** be populated with the degrees of latitude, multiplied by 10.
        */
        latitude  INTEGER (-900..900)
    }
}

/**
* This data structure is used to represent a timestamp, expressed in UTC. Implementations **SHALL** convert any
* local times to UTC before encoding them into this structure.
*/
Timestamp ::= [APPLICATION 1] SEQUENCE {
    /**
    * The year of the timestamp.
    */
    year INTEGER (2026..2281),
    /**
    * The number of the day in the above year, where the 1st of January is day number 1.
    */
    day INTEGER (1..366),
    /**
    * The number of minutes into the above day, where 0 minutes is 00:00 and 1439 minutes is 23:59.
    */
    time INTEGER (0..1439)
}

/**
* This data structure is used to represent a timestamp, including seconds, expressed in UTC.
* Implementations **SHALL** convert any local times to UTC before encoding them into this structure.
*/
TimestampSeconds ::= [APPLICATION 16] SEQUENCE {
    /**
    * The year of the timestamp.
    */
    year INTEGER (2026..2281),
    /**
    * The number of the day in the above year, where the 1st of January is day number 1.
    */
    day INTEGER (1..366),
    /**
    * The number of second into the above day, where 0 seconds is 00:00:00 and 864000 seconds is 23:59:59.
    */
    time INTEGER (0..86400)
}

/**
* This enumeration is used to describe the variety of a shared vehicle. Its values are taken from NeTEx's
* `PersonalVehicleCategory` per [](cite:cents16614-5 "10.1.4.3.4.2").
*/
SharedVehicleVariety ::= ENUMERATED {
    /**
    * Scooter - small wheeled low mobile platform.
    */
    scooter (0),
    /**
    * Bicycle.
    */
    bicycle (1),
    /**
    * Tricycle.
    */
    tricycle (2),
    /**
    * Tandem bicycle.
    */
    tandem (3),
    /**
    * Moped (Small motorbike).
    */
    moped (4),
    /**
    * Motorcycle.
    */
    motorcycle (5),
    /**
    * Motorcycle.
    */
    quadbike (6),
    /**
    * Car of any size.
    */
    car (7),
    /**
    * Extremely small vehicle.
    */
    microCar (8),
    /**
    * Very small vehicle.
    */
    miniCar (9),
    /**
    * Small vehicle.
    */
    smallCar (10),
    /**
    * Compact vehicle.
    */
    mediumCar (11),
    /**
    * Large vehicle.
    */
    largeCar (12),
    /**
    * Minivan.
    */
    minivan (13),
    /**
    * Large people transporter / minibus.
    */
    transporter (14),
    /**
    * Snowmobile.
    */
    snowmobile (15),
    /**
    * Other category.
    */
    other (16),
    ...
}

/**
* This enumeration is used to describe the propulsion method of a shared vehicle. Its values are taken from NeTEx's
* `PropulsionType` per [](cite:cents16614-5 "10.1.4.3.2.2").
*/
SharedVehiclePropulsionType ::= ENUMERATED {
    /**
    * Internal combustion of any sort.
    */
    combustion (0),
    /**
    * Electric/Combustion Hybrid.
    */
    hybrid (1),
    /**
    * Human powered (pedal, scoot etc).
    */
    human (2),
    /**
    * Human power with electric assistance.
    */
    electricAssist (3),
    /**
    * Other power.
    */
    other (4),
    ...
}

/**
* This enumeration is used to describe the return constraints of a shared Vehicle. Its values are taken from [](cite:gbfs).
*/
SharedVehicleReturnConstraint ::= ENUMERATED {
    /**
    * The vehicle can be returned anywhere permitted within the service area.
    */
    freeFloating (0),
    /**
    * The vehicle has to be returned to the same station from which it was initially rented.
    */
    roundtripStation (1),
    /**
    * The vehicle has to be returned to any station within the service area.
    */
    anyStation (2),
    /**
    * The vehicle can be returned to any station, or anywhere else permitted within the service area.
    */
    hybrid (3),
    ...
}

/**
* This class defines data element formats for use in extensible data containers used throughout this standard.
*
* Each object of this class identifies a data element format and specifies the ASN.1 type used to represent its
* contents, the encoding rules used to encode those contents, and the type used to express constraints on its values
* in certificates.
*
* Data element formats are identified by their `id`. This permits additional data element formats to be defined
* without modifying the structures in which they are carried.
*/
DATA-ELEMENT ::= CLASS {
    /**
    * The data element identifier format is constructed according to one of the following options:
    * 1. The literal character `+` (`U+002B`, PLUS SIGN), concatenated with a 2-character uppercase [](cite:iso3166-1) country
    *    code, concatenated with a string chosen by the national standards body of that country.
    * 2. The literal character `_` (`U+005F`, LOW LINE), concatenated with a 4-character ERA Organisation Code per
    *    [](cite:cid2018-1614 "II.3.2.4") or RICS, concatenated with a string chosen by that company.
    * 4. The literal character string `!I` (`U+0021`, EXCLAMATION MARK, `U+0049`, Latin Capital Letter I),
    *    concatenated with a string chosen by the issuer. This variant **SHALL** be construed as equivalent to the
    *    corresponding 2nd variant. It **SHALL** be used where possible to avoid repetition of the issuer's company code.
    *    It **SHALL NOT** be used where its meaning could be ambiguous.
    * 5. The literal character string `!C` (`U+0021`, EXCLAMATION MARK, `U+0043`, Latin Capital Letter C),
    *    concatenated with a string chosen by the carrier. This variant **SHALL** be construed as equivalent to the
    *    corresponding 2nd variant. It **SHALL** be used where possible to avoid repetition of the carriers's company
    *    code. It **SHALL NOT** be used where its meaning could be ambiguous, for example when multiple carriers are involved.
    * 6. The literal character string `!P` (`U+0021`, EXCLAMATION MARK, `U+0050`, Latin Capital Letter P),
    *    concatenated with a string chosen by the product owner. This variant **SHALL** be construed as equivalent to the
    *    corresponding 2nd variant. It **SHALL** be used where possible to avoid repetition of the product owners's
    *    company code. It **SHALL NOT** be used where its meaning could be ambiguous.
    * 7. The literal character `*` (`U+002A`, ASTERISK), concatenated with privately chosen string. **Note:** this variant has no guarantees
    *    of avoiding clashes in assignment, and **SHOULD NOT** be used unless no other option is available.
    *    If an organisation has a ERA Organisation Code or a RICS, this variant **SHALL NOT** be used.
    * 8. Any other string, as assigned in this standard. Unregistered values of this variant **SHALL NOT** be used.
    *
    * The 1st and 2nd variant **SHOULD** be registered _before_ their first use.
    * The 4th, 5th, and 6th variants cannot be registered, as they are equivalent to the corresponding 2nd variant.
    * The 8th variant **SHALL** be registered _before_ its first use.
    * Registrations **SHALL** be made with [insert registration authority].
    */
    &id VisibleString (SIZE(1..8)) UNIQUE,
    /**
    * The data structure that describes the contents of this data element.
    */
    &Type,
    /**
    * An object identifier specifying which of the ASN.1 encoding rules used to encode `Type` into an `OCTET STRING`
    * for the placing of this data element into a barcode.
    */
    &encoding OBJECT IDENTIFIER,
    /**
    * A data structure to be used within a certificate to place constraints on the possible values of a data
    * element of this variety. It **SHALL** be encoded into an `OCTET STRING` for inclusion in the certificate as
    * specified by `encoding` object identifier. It **MAY** be the null type, if no constraints ever need to be placed
    * on the data element.
    */
    &Constraints
} WITH SYNTAX {
    &Type IDENTIFIED BY &id ENCODED WITH &encoding CONSTRAINED BY &Constraints
}

/**
* This Object Identifier has been assigned by [](cite:x690) to identify the Basic Encoding Rules.
* This **SHALL** be used within a {@link DATA-ELEMENT} object to signify that it is encoded with the BER.
*/
berEncoding OBJECT IDENTIFIER ::= {joint-iso-itu-t(2) asn1(1) ber-encoding(1)}

/**
* This Object Identifier has been assigned by [](cite:x690) to identify the Canonical Encoding Rules.
* This **SHALL** be used within a {@link DATA-ELEMENT} object to signify that it is encoded with the CER.
*/
cerEncoding OBJECT IDENTIFIER ::= {joint-iso-itu-t(2) asn1(1) ber-derived-encoding(2) canonical(0)}

/**
* This Object Identifier has been assigned by [](cite:x690) to identify the Distinguished Encoding Rules.
* This **SHALL** be used within a {@link DATA-ELEMENT} object to signify that it is encoded with the DER.
*/
derEncoding OBJECT IDENTIFIER ::= {joint-iso-itu-t(2) asn1(1) ber-derived-encoding(2) distinguished(1)}

/**
* This Object Identifier has been assigned by [](cite:x691) to identify the Canonical Aligned Packed Encoding Rules.
* This **SHALL** be used within a {@link DATA-ELEMENT} object to signify that it is encoded with the CAPER.
*/
caperEncoding OBJECT IDENTIFIER ::= {joint-iso-itu-t(2) asn1(1) packed-encoding(3) canonical(1) aligned(0)}

/**
* This Object Identifier has been assigned by [](cite:x691) to identify the Canonical Unaligned Packed Encoding Rules.
* This **SHALL** be used within a {@link DATA-ELEMENT} object to signify that it is encoded with the CUPER.
*/
cuperEncoding OBJECT IDENTIFIER ::= {joint-iso-itu-t(2) asn1(1) packed-encoding(3) canonical(1) unaligned(1)}

/**
* This Object Identifier **SHALL** be used within a {@link DATA-ELEMENT} object to signify that a data element contains raw bytes.
* It is only permitted when the data element is of the `OCTET STRING` type.
*/
rawEncoding OBJECT IDENTIFIER ::= {iso(1) identified-organization(3) dod(6) internet(1) private(4) enterprise(1)
    uic(17218) fcb(1) bt4pt(2) encoding(10) raw(0)}

/**
* This Object Identifier **SHALL** be used within a {@link DATA-ELEMENT} object to signify that a data element contains no data.
* It is only permitted when the data element is of the null type.
*/
nullEncoding OBJECT IDENTIFIER ::= {iso(1) identified-organization(3) dod(6) internet(1) private(4) enterprise(1)
    uic(17218) fcb(1) bt4pt(2) encoding(10) null(1)}

/**
* Generic data container.
* @ElementSet Set of {@link DATA-ELEMENT} objects that are permitted as contents. This set **SHOULD** be extensible.
*/
Data{DATA-ELEMENT: ElementSet} ::= [APPLICATION 3] SEQUENCE {
    /**
    * This field signifies the criticality of this data element.
    *
    * If the data format is not recognised, or can't be processed, and it is marked critical, the ticket **SHALL** be
    * treated as invalid; otherwise, an implementation **SHALL** ignore extensions not understood.
    */
    critical    BOOLEAN,
    /**
    * This field identifies which type of data element is encoded.
    * Its value is used to identify which type is contained within the `value` field, and what encoding has been used
    * for it.
    */
    format      DATA-ELEMENT.&id({ElementSet}),
    /**
    * This field contains the type identified by the `format` field, encoded according to the encoding given in the
    * corresponding {@link DATA-ELEMENT} object.
    */
    value       OCTET STRING (CONTAINING DATA-ELEMENT.&Type({ElementSet}{@format}))
}

DataAuthorization{DATA-ELEMENT: ElementSet} ::= SEQUENCE (SIZE(1..64)) OF DataAuthorizationEntry{{ElementSet}}

DataAuthorizationEntry{DATA-ELEMENT: ElementSet} ::= SEQUENCE {
    /**
    * This field identifies the type of data element to which this entry applies.
    */
    format      DATA-ELEMENT.&id({ElementSet}),
    /**
    * This field contains the constraints type identified by the `format` field, encoded according to the encoding
    * given in the corresponding {@link DATA-ELEMENT} object, regardless of the encoding of the structure containing
    * this entry.
    */
    constraint  OCTET STRING (CONTAINING DATA-ELEMENT.&Constraints({ElementSet}{@format}))
}

/**
* A generic container for the conveyance of Digital Signature Scheme signatures, i.e. ECDSA.
* @len The length, in bytes, of each of `r` and `s`. That is, half the total signature length.
*/
DSSSignature{INTEGER: len} ::= SEQUENCE {
    /**
    * The output r of the DSS signature process.
    */
    r OCTET STRING (SIZE(len)),
    /**
    * The output s of the DSS signature process.
    */
    s OCTET STRING (SIZE(len))
}

/**
* @len The length, in bytes, required to represent the X coördinate on a curve.
*/
ECPublicKey{INTEGER: len} ::= SEQUENCE {
    /**
    * An indicator of the Y coördinate of the elliptic curve point being odd or even.
    * This field **SHALL** be `FALSE` if the first byte of the [](cite:sec1) compressed encoding of this point would be `02h`,
    * and **SHALL** be `TRUE` if the first byte of the [](cite:sec1) compressed encoding of this point would be `03h`.
    */
    yIsOdd BOOLEAN,
    /**
    * The X coördinate of the elliptic curve point.
    */
    x OCTET STRING (SIZE(len))
}

END
