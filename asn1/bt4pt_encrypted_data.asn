/**
* BT4PT Encrypted Data - DRAFT.
*/
BT4PT-EncryptedDataV1-0 {
    iso(1) identified-organization(3) dod(6) internet(1) private(4) enterprise(1) uic(17218) fcb(1) bt4pt(2) encryptedData(11) v1(1) 0
} DEFINITIONS ::= BEGIN

EXPORTS EncryptedData, encryptedData;
IMPORTS CompanyCode, DATA-ELEMENT, Data, cuperEncoding
 FROM BT4PT-GeneralElementsV1-0 { iso(1) identified-organization(3) dod(6) internet(1) private(4) enterprise(1) uic(17218) fcb(1) bt4pt(2) general(1) v1(1) 0 }
 luggageTag
 FROM BT4PT-LuggageTagV1-0 { iso(1) identified-organization(3) dod(6) internet(1) private(4) enterprise(1) uic(17218) fcb(1) bt4pt(2) luggageTag(12) v1(1) 0 };

/**
* This structure carries data to be included in an envelope that is readable only by the parties to which it is encrypted.
*
* The data elements are encrypted with a Content Encryption Key that is used only once. The Content Encryption Key is
* then wrapped for each recipient, using a key derived from an X25519 key agreement between an ephemeral key pair
* generated by the issuer and a long-term key pair of the recipient.
*
* The Content Encryption Key is a 128-bit key, which **SHALL** be generated by a cryptographically secure pseudo-random
* number generator for each `EncryptedData` value, and **SHALL NOT** be used for any other encryption.
*/
EncryptedData ::= SEQUENCE {
    /**
    * The information each recipient requires to recover the Content Encryption Key.
    */
    header      EncryptedDataHeader,
    /**
    * The encrypted data, being the ciphertext followed by the 16-byte authentication tag, as output by AES-128-GCM per
    * [](cite:nist-sp800-38d), with:
    * - the key being the Content Encryption Key.
    * - the 96-bit initialisation vector consisting of 12 null bytes.
    * - the additional authenticated data being the Canonical Unaligned Packed Encoding Rules encoding of the `header` field.
    * - the plaintext being the Canonical Unaligned Packed Encoding Rules encoding of {@link InnerData}.
    */
    ciphertext  OCTET STRING
}

encryptedData DATA-ELEMENT ::= { EncryptedData IDENTIFIED BY "ENC1" ENCODED WITH cuperEncoding CONSTRAINED BY NULL }

/**
* This header contains the information identifying to whom the data is encrypted, and the data required to obtain
* the Content Encryption Key.
*
* It contains an ephemeral X25519 key and the wrapped key per recipient. The ephemeral key pair **SHALL** be generated
* by a cryptographically secure pseudo-random number generator for each encrypted data element, and **SHALL NOT** be
* used for any other encrypted data element. The ephemeral private key **SHALL** be destroyed once the wrapping key of
* every recipient has been derived.
*/
EncryptedDataHeader ::= SEQUENCE {
    /**
    * The public key of an ephemeral X25519 key pair, encoded as specified in [](cite:rfc7748).
    */
    ephemeralPublicKey  OCTET STRING (SIZE(32)),
    /**
    * The recipients of the encrypted data.
    * No two entries **SHALL** have the same `key`.
    */
    recipients          SEQUENCE SIZE(1..32) OF Recipient
}

/**
* This structure contains the per-recipient info required to obtain the Content Encryption Key.
*
* The Content Encryption Key **SHALL** be wrapped using the AES Key Wrap algorithm of [](cite:rfc3394), using the
* default initial value, and a 256-bit wrapping key derived as follows:
* 1. Let `SK` be the 32-byte output of the X25519 function of [](cite:rfc7748), applied to the ephemeral private key
*    and the long-term public key identified by `key` when encrypting, or to the long-term private key identified
*    by `key` and `ephemeralPublicKey` when decrypting.
* 2. If `SK` consists only of null bytes, the key agreement has failed, and the wrapping key **SHALL NOT** be derived.
* 3. The wrapping key is the 32-byte output of HKDF with SHA-256 per [](cite:rfc5869), with the input being the keying
*    material `SK`, the salt being the value of `ephemeralPublicKey`, and info being the ASCII string
*    `BT4PT-EncryptedDataV1-0` followed by the 32-byte long-term public key identified by `key`, encoded as specified
*    in [](cite:rfc7748).
*/
Recipient ::= SEQUENCE {
    /**
    * Identifies the long-term X25519 key of the recipient to which the Content Encryption Key is wrapped.
    */
    key         RecipientKey,
    /**
    * The wrapped Content Encryption Key.
    */
    wrappedKey  OCTET STRING (SIZE(24))
}

/**
* This data structure identifies the long-term X25519 key of a recipient, by the Key Agreement Key ID of the
* [Key Agreement Certificate](#ka-certs) certifying it.
*/
RecipientKey ::= SEQUENCE {
    /**
    * The Security Provider holding the long-term key, being the Company Code in the Subject Alternative Name extension
    * of the Key Agreement Certificate.
    */
    securityProvider    CompanyCode,
    /**
    * The Key ID in the Key Agreement Key ID extension of the Key Agreement Certificate.
    */
    keyId               INTEGER (1..65536)
}

/**
* This structure, when encoded with the Canonical Unaligned Packed Encoding Rules, is the plaintext that is to be encrypted and
* included in a {@link EncryptedData} instance.
*/
InnerData ::= SEQUENCE (SIZE(1..16)) OF Data{{EncryptedDataElements}} (WITH COMPONENTS {
    ...,
    format (ALL EXCEPT ("!I" | "!C" | "!P"))
})

/**
* These are the data elements that may appear in an encrypted data element.
* Note: other data elements, not defined in this standard, are also permitted to appear.
*/
EncryptedDataElements DATA-ELEMENT ::= {
    luggageTag,
    ...
}

END
