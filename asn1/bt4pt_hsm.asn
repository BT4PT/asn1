/**
* A record to include in the BT4PT barcode header SecurityProviderSignedData to allow for tracing which HSM generated a signature.
*/
BT4PT-HSMTraceV1-0 {
    iso(1) identified-organization(3) dod(6) internet(1) private(4) enterprise(1) uic(17218) fcb(1) bt4pt(2) hsm(6) v1(1) 0
} DEFINITIONS ::= BEGIN

EXPORTS HSMTrace, HSMTraceConstraints, hsmTraceData, HSMAlgorithmIdentifier, HSMPublicKeyInfo,
 AuthorisationGrant, TBSAuthorisationGrant, GrantAuthorityKeyChange, TBSGrantAuthorityKeyChange;
IMPORTS DATA-ELEMENT, cuperEncoding
 FROM BT4PT-GeneralElementsV1-0 { iso(1) identified-organization(3) dod(6) internet(1) private(4) enterprise(1) uic(17218) fcb(1) bt4pt(2) general(1) v1(1) 0 };

HSMTrace ::= SEQUENCE {
    /**
    * An opaque random ID. This value **SHALL** be assigned by a cryptographically secure pseudo-random number generator
    *  at the personalisation of the Hardware Security Module.
    */
    hsmId               OCTET STRING (SIZE(8)),
    /**
    * ID of the key slot of the HSM that was used to generate the signature.
    */
    keySlot             INTEGER (0..255),
    /**
    * Monotonically increasing global counter of signatures performed by the HSM, encoded as a big-endian integer.
    * That is, this counter is for the entire HSM, not merely one key slot.
    * The sequence need not be contiguous; gaps are permitted between values, as long as the counter does not go backwards.
    *
    * This counter **SHALL** be maintained by the HSM itself, **SHALL** be incremented for each
    *   signature generated, successful or not.
    *
    * Wrap-around is not permitted; once the counter reaches its limit, the HSM is considered spent.
    * A HSM whose signature counter has reached its maximum value **SHALL NOT** generate any further signatures.
    */
    signatureCounter    OCTET STRING (SIZE(4))
}

/**
* The constraints placed on the HSM Trace data element by a Security Provider Data Authorisation record. They bind the key pair
* certified by a certificate to the Hardware Security Module holding it.
*
* As Security Provider Data Authorisation is cumulative, every Certificate Authority in the chain of a HSM-held key has to permit
* the HSM Trace data element, but only the Issuing Certificate Authority can know which Hardware Security Modules hold the
* key. `permittedHsmId` is therefore optional, and an entry without it permits the data element without restricting its
* `hsmId`.
*
* When any Security Provider Data Authorisation record in the certificate chain of an envelope contains an entry for the HSM Trace
* data element which has `permittedHsmId`, the Security Provider signed data of the envelope **SHALL** contain exactly
* one HSM Trace data element, and its `hsmId` **SHALL** be equal to the `permittedHsmId` of every such entry. Otherwise,
* the envelope **SHALL** be construed as invalid.
*/
HSMTraceConstraints ::= SEQUENCE {
    /**
    * The `hsmId` value of the Hardware Security Module which holds the private key, and is thus permitted to sign
    * envelopes under the certificate.
    */
    permittedHsmId     OCTET STRING (SIZE(8)) OPTIONAL
}

/**
* When the private key of an End-Entity is held in a Hardware Security Module, the Security Provider **SHALL** include
* this HSM Trace data element in the Security Provider signed data of each envelope signed with that key. This allows
* tracing of the source of an envelope, and the revocation of keys only from a given point in time onward.
*
* The HSM **SHALL** itself set the `hsmId`, `keySlot`, and `signatureCounter` of the HSM Trace data element in the data it
* signs, or **SHALL** verify that they are equal to its own identifier, the key slot used, and the value of its signature
* counter for that signature, and refuse to sign otherwise. The values of this data element **SHALL NOT** be alterable by
* any entity outside the HSM.
*
* When an End-Entity Certificate is issued to a key pair held in a HSM, the Issuing Certificate Authority **SHALL**
* include `permittedHsmId` in the entry for this data element in the Security Provider Data Authorisation of the End-Entity Certificate.
* When an End-Entity Certificate is not issued to a key pair held in a HSM, the Certificate Authority **SHALL NOT**
* permit this data element in the Security Provider Data Authorisation of the certificate.
*/
hsmTraceData DATA-ELEMENT ::= { HSMTrace IDENTIFIED BY "HSM1" ENCODED WITH cuperEncoding CONSTRAINED BY HSMTraceConstraints }

/**
* This structure encodes an algorithm identifier, as used by the interface to End-Entity Hardware Security Modules.
*
* This type is a restriction of the `AlgorithmIdentifier` type of [](cite:rfc5280) to algorithms whose parameters are
* either absent or a named curve object identifier. For such algorithms, its encoding per the Distinguished Encoding
* Rules is identical to that of `AlgorithmIdentifier`.
*/
HSMAlgorithmIdentifier ::= SEQUENCE {
    /**
    * The object identifier of the algorithm.
    */
    algorithm   OBJECT IDENTIFIER,
    /**
    * The parameters of the algorithm. For `id-ecPublicKey` this **SHALL** be the object identifier of the named curve,
    * per [](cite:rfc5480). For all other algorithms used with this type, this **SHALL** be absent.
    */
    parameters  OBJECT IDENTIFIER OPTIONAL
}

/**
* This structure encodes a public key, as used by the interface to End-Entity Hardware Security Modules.
*
* This type has the same encoding per the Distinguished Encoding Rules as the `SubjectPublicKeyInfo` type of 
* [](cite:rfc5280). Elliptic curve public keys **SHALL** be encoded per [](cite:rfc5480), with the point in the
* uncompressed form, and Ed25519 and Ed448 public keys per [](cite:rfc8410).
*/
HSMPublicKeyInfo ::= SEQUENCE {
    /**
    * The type of the key.
    */
    algorithm           HSMAlgorithmIdentifier,
    /**
    * The public key itself.
    */
    subjectPublicKey    BIT STRING
}

/**
* Thin structure encodes an authorisation grant, issued by a grant authority to a Hardware Security Module.
* It **SHALL** be encoded per the Distinguished Encoding Rules.
*/
AuthorisationGrant ::= SEQUENCE {
    /**
    * The content of the grant.
    */
    tbsGrant            TBSAuthorisationGrant,
    /**
    * The algorithm with which the grant is signed. This **SHALL** be compatible with the grant authority key of the
    * Hardware Security Module.
    */
    signatureAlgorithm  HSMAlgorithmIdentifier,
    /**
    * The signature of the grant authority over the encoding of `tbsGrant` per the Distinguished Encoding Rules.
    * For ECDSA, this **SHALL** contain the `Ecdsa-Sig-Value` structure, per [](cite:rfc5758).
    */
    signature           BIT STRING
}

/**
* This structure encodes a the signed content of an authorisation grant.
*/
TBSAuthorisationGrant ::= [APPLICATION 14] IMPLICIT SEQUENCE {
    /**
    * The `hsmId` of the Hardware Security Module to which the grant is issued.
    */
    hsmId       OCTET STRING (SIZE(8)),
    /**
    * The challenge most recently generated by the Hardware Security Module.
    */
    challenge   OCTET STRING (SIZE(16)),
    /**
    * The highest value the signature counter of the Hardware Security Module may reach.
    */
    grantLimit  INTEGER (0..4294967295)
}

/**
* This structure encodes an instruction, from a grant authority to its Hardware Security Module, to replace its grant
* authority key. It **SHALL** be encoded per the Distinguished Encoding Rules.
*/
GrantAuthorityKeyChange ::= SEQUENCE {
    /**
    * The content of the instruction.
    */
    tbsKeyChange        TBSGrantAuthorityKeyChange,
    /**
    * The algorithm with which the instruction is signed. This **SHALL** be compatible with the current grant authority
    * key of the Hardware Security Module.
    */
    signatureAlgorithm  HSMAlgorithmIdentifier,
    /**
    * The signature of the current grant authority over the encoding of `tbsKeyChange` per the Distinguished Encoding
    * Rules. For ECDSA, this **SHALL** contain the `Ecdsa-Sig-Value` structure, per [](cite:rfc5758).
    */
    signature           BIT STRING
}

/**
* The signed content of an instruction to replace the grant authority key.
*/
TBSGrantAuthorityKeyChange ::= [APPLICATION 15] IMPLICIT SEQUENCE {
    /**
    * The `hsmId` of the Hardware Security Module whose grant authority key is to be replaced.
    */
    hsmId       OCTET STRING (SIZE(8)),
    /**
    * The challenge most recently generated by the Hardware Security Module.
    */
    challenge   OCTET STRING (SIZE(16)),
    /**
    * The new grant authority key.
    */
    newKey      HSMPublicKeyInfo
}

END
