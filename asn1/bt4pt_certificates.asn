/**
* BT4PT Certificates - DRAFT.
*/
BT4PT-CertificatesV1-0 {
    iso(1) identified-organization(3) dod(6) internet(1) private(4) enterprise(1) uic(17218) fcb(1) bt4pt(2) certificates(7) v1(1) 0
} DEFINITIONS ::= BEGIN

EXPORTS EndEntityCertificate;
IMPORTS CompanyCode, Data, ECPublicKey, DataAuthorization, UnicodeText, Timestamp, DATA-ELEMENT, cuperEncoding, nullEncoding
 FROM BT4PT-GeneralElementsV1-0 { iso(1) identified-organization(3) dod(6) internet(1) private(4) enterprise(1) uic(17218) fcb(1) bt4pt(2) general(1) v1(1) 0 }
 SecurityProviderDataElements
 FROM BT4PT-EnvelopeV1-0 { iso(1) identified-organization(3) dod(6) internet(1) private(4) enterprise(1) uic(17218) fcb(1) bt4pt(2) envelope(2) v1(1) 0 };

/**
* Extensions to X.509 made within this specification are identified under this following OID tree.
*/
bt4ptPkiExt OBJECT IDENTIFIER ::= {iso(1) identified-organization(3) dod(6) internet(1) private(4) enterprise(1)
    uic(17218) fcb(1) bt4pt(2) pkiExt(9)}

EndEntityCertificate ::= SEQUENCE {
    /**
    * This field **SHALL** be unique amongst all End-Entity Certificates issued by that Issuing Certificate Authority key pair.
    */
    serial                      INTEGER (1..16777216),
    /**
    * The operator of the Issuing Certificate Authority.
    */
    issuingOrg                  CompanyCode,
    /**
    * This field, together with the previous field, identifies the Issuing Certificate Authority by its [Certificate ID](#certificate-id).
    */
    caId                        INTEGER (1..65536),
    /**
    * This field, together with the next field, give the last day, in UTC, on which the certificate is valid.
    * The certificate **SHALL** be considered expired after the end of that day.
    * There is no start of validity encoded in the certificate; an End-Entity Certificate is valid from its issuance.
    * The validity of an End-Entity Certificate **SHALL NOT** extend beyond the validity of its Issuing Certificate Authority certificate.
    */
    validUntilYear              INTEGER (2026..2281),
    /**
    * The ordinal day of the year, with 1 January being day `1`.
    */
    validUntilDay               INTEGER (1..366),
    /**
    * This field contains the public key reconstruction point `P_U` as specified in [](cite:sec4).
    * Its curve **SHALL** be the curve of the Issuing Certificate Authority's public key; if it is not, the certificate
    * **SHALL** be treated as invalid.
    */
    keyData                     CHOICE {
        /**
        * A point on the [NIST P-256](cite:nist-sp800-186) curve.
        */
        nistP256    [1] ECPublicKey{32},
        /**
        * A point on the [NIST P-384](cite:nist-sp800-186) curve.
        */
        nistP384    [3] ECPublicKey{48},
        /**
        * A point on the [NIST P-521](cite:nist-sp800-186) curve.
        */
        nistP521    [4] ECPublicKey{66}
    },
    /**
    * The extensions of the certificate.
    */
    extensions                  SEQUENCE (SIZE(0..15)) OF CertificateExtension
}

/**
* This class defines extensions to X.509 and End-Entity Certificates for use in this standard.
*
* Each object of this class identifies a extension and specifies the ASN.1 type used to represent its contents and the
* encoding rules used to encode those contents.
*
* In End-Entity Certificates extensions are identified by their `id`.
* If `&id` is not set, then the extension may not appear in an End-Entity Certificates, only an X.509 certificate.
*
* In X.509 Certificates they are identified by their `oid`. The `extnValue` of such an extension **SHALL** contain the
* encoding of the extension's `&Type` using the encoding rules identified by the object's `&encoding`.
* Note: this may not be DER and is frequently UPER.
*/
CERTIFICATE-EXTENSION ::= CLASS {
    /**
    * The extension identifier format is constructed according to one of the following options:
    * 1. The literal character `+` (`U+002B`, PLUS SIGN), concatenated with a 2-character uppercase [](cite:iso3166-1) country
    *    code, concatenated with a string chosen by the national standards body of that country.
    * 2. The literal character `_` (`U+005F`, LOW LINE), concatenated with a 4-character ERA Organisation Code per
    *    [](cite:cid2018-1614 "II.3.2.4") or RICS, concatenated with a string chosen by that company.
    * 3. The literal character `*` (`U+002A`, ASTERISK), concatenated with privately chosen string. **Note:** this variant has no guarantees
    *    of avoiding clashes in assignment, and **SHOULD NOT** be used unless no other option is available.
    *    If an organisation has a ERA Organisation Code or a RICS, this variant **SHALL NOT** be used.
    * 4. Any other string, as assigned in this standard. Unregistered values of this variant **SHALL NOT** be used.
    *
    * The 1st and 2nd variant **SHOULD** be registered _before_ their first use.
    * The 4th variant **SHALL** be registered _before_ its first use.
    * Registrations **SHALL** be made with [insert registration authority].
    */
    &id VisibleString (SIZE(1..8) ^ (ALL EXCEPT ("!I" | "!C" | "!P"))) UNIQUE OPTIONAL,
    /**
    * The Object Identifier for this extension.
    */
    &oid OBJECT IDENTIFIER UNIQUE,
    /**
    * The data structure that describes the contents of this extension.
    */
    &Type,
    /**
    * An object identifier specifying which of the ASN.1 encoding rules used to encode `Type` into an `OCTET STRING`
    * for the placing of this extension into a certificate.
    */
    &encoding OBJECT IDENTIFIER
} WITH SYNTAX {
    &Type [IDENTIFIED BY &id] WITH OID &oid ENCODED WITH &encoding
}

/**
* This set defines the BT4PT specific certificate extensions which are permissible to appear on X.509 Certificates.
*/
CertificateExtensions CERTIFICATE-EXTENSION ::= {
    specimenPoisonExt |
    securityProviderDataAuthorizationExt |
    certificateIdExt |
    eeCertCRLExt |
    subordinateCertificateRepositoryV1-0Ext |
    keyAgreementKeyIdExt,
    ...
}

/**
* This data structure encodes an extension to an End-Entity Certificate, identified by its `id`.
* An extension without an `id` **SHALL NOT** appear in an End-Entity Certificate.
*/
CertificateExtension ::= [APPLICATION 3] SEQUENCE {
    /**
    * This field allows for the introduction of new, security critical, elements in the future.
    * If an extension alters the validity of a certificate in a way which would cause Ticket Inspection Devices unaware of
    * the semantics of the extension to treat the ticket as valid where it shouldn't have been, this field **SHALL** be `TRUE`.
    */
    critical    BOOLEAN,
    /**
    * This field identifies which type of data element is encoded.
    * Its value is used to identify which type is contained within the `value` field, and what encoding has been used
    * for it.
    */
    format      CERTIFICATE-EXTENSION.&id({EECertificateExtensions}),
    /**
    * This field contains the type identified by the `format` field, encoded according to the encoding given in the
    * corresponding {@link CERTIFICATE-EXTENSION} object.
    */
    value       OCTET STRING (CONTAINING CERTIFICATE-EXTENSION.&Type({EECertificateExtensions}{@format}))
}

/**
* This set defines the BT4PT specific certificate extensions which are permissible to appear on End-Entity Certificates.
*/
EECertificateExtensions CERTIFICATE-EXTENSION ::= {
    specimenPoisonExt |
    securityProviderDataAuthorizationExt,
    ...
}

id-specimenPoison OBJECT IDENTIFIER ::= {bt4ptPkiExt specimenPoison(0)}
/**
* Any envelope whose certificate chain contains, in any certificate, the Specimen Poison extension **SHALL** be considered
* a specimen, regardless of the value of any other specimen indicator in the envelope or its data elements.
*
* Certificate Authorities **SHALL** include this extension when a certificate they issue is not to be used in production.
*/
specimenPoisonExt CERTIFICATE-EXTENSION ::= { NULL IDENTIFIED BY "SP" WITH OID id-specimenPoison ENCODED WITH nullEncoding }

id-securityProviderDataAuthorization OBJECT IDENTIFIER ::= {bt4ptPkiExt securityProviderDataAuthorization(1)}
/**
* The Security Provider Data Authorisation extension specifies which Security Provider signed data elements may be included in an
* envelope signed under the certificate, and which constraints apply to them. A certificate which contains no Security Provider Data
* Authorisation record places no restriction on the data elements of envelopes signed under it.
*
* A Security Provider Data Authorisation record **SHALL NOT** contain more than one entry with the same `format`.
*/
securityProviderDataAuthorizationExt CERTIFICATE-EXTENSION ::= { DataAuthorization{{SecurityProviderDataElements}} IDENTIFIED BY "ID" WITH OID id-securityProviderDataAuthorization ENCODED WITH cuperEncoding }

id-certificateId OBJECT IDENTIFIER ::= {bt4ptPkiExt certificateId(2)}
/**
* This extension is placed in the X.509 certificate of an Issuing Certificate Authority, and contains its CA ID.
*
* The Certificate ID of an Issuing Certificate Authority is the tuple of the Company Code contained in the
* `id-otherNameCompanyCode` `otherName` of the Subject Alternative Name extension of its certificate, and the CA ID
* contained in this extension. The Certificate ID **SHALL** uniquely identify a key pair within the BT4PT PKI.
* An entity **SHALL NOT** assign the same CA ID to two different key pairs.
*
* An End-Entity Certificate is issued by the Issuing Certificate Authority whose Certificate ID is equal to the
* `issuingOrg` and `caId` of the End-Entity Certificate.
*
* An Issuing Certificate Authority certificate **MAY** be re-issued with updated metadata (for example, changed Security
* Provider Data Authorisation) whilst retaining the same Certificate ID, provided that the public key is unchanged.
*/
certificateIdExt CERTIFICATE-EXTENSION ::= { INTEGER (1..65536) WITH OID id-certificateId ENCODED WITH cuperEncoding }

id-eeCertCRL OBJECT IDENTIFIER ::= {bt4ptPkiExt eeCertCRL(3)}
/**
* This extension **SHALL** contain a `https://` URL at which the [Certificate Revocation List](cite:x509) covering the
* End-Entity Certificates it has issued may be retrieved.
* That is, it is not the CRL covering the certificate itself, but the complete CRL for all subordinate certificates
* directly issued by the given certificate.
* The file at the URL **SHALL** be openly accessible on the Internet without any authentication, free of charge.
*/
eeCertCRLExt CERTIFICATE-EXTENSION ::= { VisibleString WITH OID id-eeCertCRL ENCODED WITH cuperEncoding }

/**
* The Revocation Notice informs inspection staff and Ticket Inspection Devices of the reason for the revocation of a
* certificate, and of how envelopes signed under it are to be treated. It consists of a coded reason, a coded action,
* and an optional notice in one or more languages to be displayed to inspection staff.
*
* Every entry of a Certificate Revocation List **SHALL** contain exactly one Revocation Notice.
*
* Certificate Authorities **SHALL** include a textual notice in `localisedNotices` when the circumstances of revocation
* warrant further explanation to ticket control staff. The textual notice **SHOULD** be provided in the predominant
* languages of the area in which envelopes relating to this revocation are likely to be encountered. Where the coded
* `reason` and `action` convey all the necessary information, `localisedNotices` **MAY** be empty.
*/
RevocationNotice ::= SEQUENCE {
    /**
    * The reason for the revocation, as it is to be presented to inspection staff. Ticket Inspection Devices **SHOULD**
    * display a description of this reason in the language of the inspection staff.
    */
    reason              RevocationNoticeReason,
    /**
    * The action to be taken by inspection staff, or a Ticket Inspection Device, upon the inspection of an envelope
    * signed under the revoked certificate.
    */
    action              InspectorAction         DEFAULT reject,
    /**
    * The end of the period during which the `action` applies. This field **SHALL** be present if, and only if, `action`
    * is `acceptUntil`.
    */
    actionEnd           Timestamp               OPTIONAL,
    /**
    * Each entry in `localisedNotices` **SHOULD** convey the same information in a different language.
    * This field **MAY** be empty if the circumstances are described entirely by the above fields.
    * The Ticket Inspection Device selects which language, of those provided, is most appropriate to be displayed.
    */
    localisedNotices    SEQUENCE OF UnicodeText
}

/**
* The reason for the revocation of a certificate, as presented to inspection staff.
*
* The values 1 to 3 are aligned with the `HotListStatusCode` of [](cite:en1545-1). Other values below 64 are reserved
* for alignment with [](cite:en1545-1).
*/
RevocationNoticeReason ::= ENUMERATED {
    /**
    * No reason is given.
    */
    notGiven                (0),
    /**
    * The reason is undefined. This variant can be used when the circumstances are described entirely by the localised notices.
    */
    undefined               (1),
    /**
    * A Hardware Security Module, or other device holding the private key, has been stolen.
    */
    deviceStolen            (2),
    /**
    * A Hardware Security Module, or other device holding the private key, has been lost.
    */
    deviceLost              (3),
    /**
    * The private key is known, or suspected, to have been exposed.
    */
    keyCompromised          (64),
    /**
    * Envelopes were issued fraudulently under the certificate.
    */
    fraudulentIssuance      (65),
    /**
    * The certificate was used outside of its authorisation.
    */
    misuse                  (66),
    /**
    * The certificate was issued in error, for example with and Security Provider Data Authorisation.
    */
    issuedInError           (67),
    /**
    * The evidence of resistance of a Hardware Security Module holding the private key was withdrawn, or a component
    * not meeting the requirements of this standard was used.
    */
    uncertifiedComponent    (68),
    /**
    * The issuer or Security Provider has ceased to operate, or its contract or authorisation has ended.
    */
    issuerCeased            (69),
    /**
    * The certificate is revoked pending further investigation.
    */
    suspended               (70),
    /**
    * The key has been retired in the normal course of operations, with no security concern.
    */
    routineRetirement       (71),
    ...
}

/**
* The action to be taken upon the inspection of an envelope signed under a revoked certificate.
*/
InspectorAction ::= ENUMERATED {
    /**
    * The envelope is not to be accepted.
    */
    reject                      (0),
    /**
    * The envelope is to be accepted if the traveller presents proof of purchase, such as a receipt or booking
    * confirmation.
    */
    acceptWithProofOfPurchase   (1),
    /**
    * The envelope is to be accepted if the identity of the traveller matches that of the booking.
    */
    acceptWithIdentity          (2),
    /**
    * The envelope is to be accepted, and its details recorded and referred to the issuer.
    */
    referToIssuer               (3),
    /**
    * The envelope is to be accepted until the `actionEnd` of the Revocation Notice, and not accepted thereafter.
    */
    acceptUntil                 (4),
    /**
    * The envelope is not to be accepted, and the ticket on which it is presented is to be retained, for example in the
    * case of a ticket on secure paper.
    */
    retainDocument              (5),
    ...
}

id-revocationNotice OBJECT IDENTIFIER ::= {bt4ptPkiExt revocationNotice(4)}
revocationNoticeExt CERTIFICATE-EXTENSION ::= { RevocationNotice WITH OID id-revocationNotice ENCODED WITH cuperEncoding }

id-subordinateCertificateRepositoryV1-0 OBJECT IDENTIFIER ::= {bt4ptPkiExt subordinateCertificateRepositoryV1-0(5)}
/**
* All Certificate Authority Certificates that are not Issuing Certificate Authority Certificates, and all Issuing
* Certificate Authority Certificates whose key has been used to issue a Key Agreement Certificate, **SHALL** contain this
* extension. This extension **SHALL** contain a `https://` URL at which the Repository for the given CA
* Certificate can be retrieved. The file at the URL, as well as any URLs referenced in the repository **SHALL** be openly
* accessible on the Internet without any authentication, free of charge.
*/
subordinateCertificateRepositoryV1-0Ext CERTIFICATE-EXTENSION ::= { VisibleString WITH OID id-subordinateCertificateRepositoryV1-0 ENCODED WITH cuperEncoding }

/**
* The Last Known-good Signature Counter allows the revocation of a key held in a Hardware Security Module only into the
* future. This permits, for example, a Hardware Security Module that is known to have been stolen to be revoked, without
* invalidating the legitimate envelopes it signed before it was stolen.
*
* This extension **SHALL** only be used in a Certificate Revocation List for End-Entity Certificates.
*
* This extension **SHALL NOT** be used when there is evidence a private key has been extracted from a HSM. It is only
* suitable to use when the private key is still secured within the HSM, but the HSM is in malicious hands.
*
* When an End-Entity Certificate is listed on a Certificate Revocation List with this extension, an envelope signed
* under it **SHALL** be considered not revoked if, and only if, its Security Provider signed data contains an HSM Trace
* data element whose `hsmId` is equal to that of this extension, and whose `signatureCounter`, interpreted as a
* big-endian unsigned integer, is less than or equal to that of this extension. All other envelopes signed under that
* certificate **SHALL** be considered revoked.
*
* Before including this extension in a Certificate Revocation List, the Certificate Authority **SHALL** establish,
* based on evidence provided by the Security Provider, a counter value below which signatures can reasonably be
* considered to have been generated whilst the Hardware Security Module was under the legitimate control of the
* Security Provider. The last observed or reported signature counter value **SHALL NOT**, on its own, be considered
* sufficient evidence that all signatures up to that value were legitimately generated. The Certificate Authority
* **SHALL** consider the records of signing operations, the history of authorisation grants, the circumstances of the
* loss or theft of the Hardware Security Module, and any other relevant evidence.
*
* The Certificate Authority **MAY** select a lower counter value than the highest value supported by the available
* evidence, to account for uncertainty about the circumstances of the incident.
*
* Where the Certificate Authority cannot establish a counter value for which it has reasonable confidence that
* signatures up to that value were legitimately generated, it **SHALL NOT** use this extension.
*
* The Certificate Authority **SHALL** document the evidence used to establish the Last Known-good Signature Counter and
* **SHALL** retain this evidence as part of its certificate revocation records.
*/
LastGoodSignatureCounter ::= SEQUENCE {
    /**
    * The identifier of the HSM, as per its HSM tracing record, specified in [](#hsm-tracing).
    */
    hsmId               OCTET STRING (SIZE(8)),
    /**
    * The maximum value to accept for the signature counter.
    */
    signatureCounter    OCTET STRING (SIZE(4))
}
id-lastGoodSignatureCounter OBJECT IDENTIFIER ::= {bt4ptPkiExt lastGoodSignatureCounter(6)}
lastGoodSignatureCounterExt CERTIFICATE-EXTENSION ::= { LastGoodSignatureCounter WITH OID id-lastGoodSignatureCounter ENCODED WITH cuperEncoding }

id-onlineValidationRequiredMarker OBJECT IDENTIFIER ::= {bt4ptPkiExt onlineValidationRequiredMarker(7)}
/**
* The Online Validation Required Marker indicates that the private key corresponding to the revoked certificate is
* likely compromised, but that envelopes signed under it may nonetheless be legitimate. This extension instructs
* Ticket Inspection Devices to perform an online check against a ticket control database before accepting an envelope,
* instead of outright rejecting such envelopes.
*
* When there is a high risk of inconvenience to the travelling public by revocation, a CA **SHALL** use this extension.
* This situation arises, for example, when key has been used to issue many paper tickets whose barcodes cannot now
* be updated.
*/
onlineValidationRequiredMarkerExt CERTIFICATE-EXTENSION ::= { NULL WITH OID id-onlineValidationRequiredMarker ENCODED WITH nullEncoding }

/**
* This Extended Key Usage is placed in the X.509 certificate of a Trust Anchor.
* A Relying Party **SHALL NOT** accept a certificate as a valid point to end the validation chain on unless it is
* both in its list of trusted roots and it contains this EKU.
*/
id-trustAnchorMarker OBJECT IDENTIFIER ::= {bt4ptPkiExt trustAnchorMarker(8)}

/**
* This Extended Key Usage is placed in the X.509 certificate directly issuing End-Entity Certificates.
* A Relying Party **SHALL NOT** accept an End-Entity Certificate unless it is issued by a certificate containing this
* Extended Key Usage.
*/
id-endEntityCAMarker OBJECT IDENTIFIER ::= {bt4ptPkiExt endEntityCAMarker(9)}

/**
* This OID is used in the X.509 `GeneralName.otherName` to signify a DER-encoded `CompanyCode`.
* It is to be used in either the Subject Alternative Name or Issuer Alternative Name X.509 extensions.
*/
id-otherNameCompanyCode OBJECT IDENTIFIER ::= {bt4ptPkiExt otherNameCompanyCode(10)}

/**
* By including this OID in an X.509 certificate's Certificate Policies, the issuer is asserting conformance and
* adherence to the common certificate baseline defined by BT4PT.
*/
id-certificatePolicyBaseline OBJECT IDENTIFIER ::= {bt4ptPkiExt certificatePolicyBaseline(11)}

id-keyAgreementKeyId OBJECT IDENTIFIER ::= {bt4ptPkiExt keyAgreementKeyId(12)}
/**
* This extension is placed in a [Key Agreement Certificate](#ka-certs), and contains its Key ID.
*
* The Key Agreement Key ID of a Key Agreement Certificate is the tuple of the Company Code contained in the
* {@link id-otherNameCompanyCode} `otherName` of the Subject Alternative Name extension of the certificate, and the Key
* ID contained in this extension. It is the value used as the `RecipientKey` of [encrypted data](#encrypted-data).
* The Key Agreement Key ID **SHALL** uniquely identify a key pair within the BT4PT PKI. A Security Provider **SHALL NOT**
* assign the same Key ID to two different key pairs.
*
* A Key Agreement Certificate **MAY** be re-issued with updated metadata whilst retaining the same Key Agreement Key ID,
* provided that the public key is unchanged.
*/
keyAgreementKeyIdExt CERTIFICATE-EXTENSION ::= { INTEGER (1..65536) WITH OID id-keyAgreementKeyId ENCODED WITH cuperEncoding }

/**
* This Extended Key Usage is placed in a [Key Agreement Certificate](#ka-certs), and indicates that the certified
* X25519 key is to be used for the encryption of data to its holder, as specified in [](#encrypted-data).
* An issuer of envelopes **SHALL NOT** encrypt data to a key whose certificate does not contain this Extended Key Usage.
*/
id-keyAgreementKeyPurpose OBJECT IDENTIFIER ::= {bt4ptPkiExt keyAgreementKeyPurpose(13)}

END
