/**
* BT4PT Metadata files - DRAFT.
*/
BT4PT-MetadataV1-0 {
    iso(1) identified-organization(3) dod(6) internet(1) private(4) enterprise(1) uic(17218) fcb(1) bt4pt(2) metadata(8) v1(1) 0
} DEFINITIONS ::= BEGIN

EXPORTS SubordinateCertificateList;
IMPORTS Timestamp
 FROM BT4PT-GeneralElementsV1-0 { iso(1) identified-organization(3) dod(6) internet(1) private(4) enterprise(1) uic(17218) fcb(1) bt4pt(2) general(1) v1(1) 0 };

/**
* This structure **SHALL** be encoded using the ASN.1 Distinguished Encoding Rules and made available on the public
* URL that is referenced in the CA's X.509 certificate extensions.
*
* The data **SHALL** be presented with the `Content-Type` of `application/vnd.bt4pt.cert-list+der`.
*/
SubordinateCertificateList ::= SEQUENCE {
    /**
    * This field contains the data of the certificate list, before signing.
    */
    data        TbsSubordinateCertificateList,
    /**
    * This field **SHALL** contain a signature over the DER encoding of `TbsSubordinateCertificateList`, made using the
    * algorithm given in `signatureAlgorithm`. For ECDSA, the signature **SHALL** be the DER encoding of an
    * `ECDSA-Sig-Value`. For ML-DSA, the signature **SHALL** be the octets of the signature as specified in FIPS 204.
    * The signature **SHALL** be made using the private key corresponding to the CA certificate containing the extension
    * which references this certificate list.
    */
    signature   OCTET STRING
}

TbsSubordinateCertificateList ::= SEQUENCE {
    /**
    * A strictly increasing number. If a client sees a certificate list with a number less than or equal to the
    * greatest `manifestNumber` previously accepted for the same CA certificate it **SHALL** ignore such a list.
    */
    manifestNumber      INTEGER (0..MAX),
    /**
    * The point in time at which this certificate list was generated.
    */
    thisUpdate          Timestamp,
    /**
    * The point in time that clients **SHOULD** next refetch this list.
    * Note: a cached manifest that is older than its `recommendRefresh` does not immediately invalidate all certificates
    * listed within, it **MAY** be used until a new certificate list can be downloaded.
    */
    recommendRefresh    Timestamp,
    /**
    * An identifier of the algorithm used to calculate the wrapping `signature`.
    */
    signatureAlgorithm  OBJECT IDENTIFIER,
    /**
    * A list of all subordinate X.509 certificates directly issued by the relevant CA.
    */
    certificateList     SEQUENCE OF CertificateEntry
}

/**
* One, and only one of these entries **SHALL** exist for each certificate the CA has issued.
*/
CertificateEntry ::= SEQUENCE {
    /**
    * The SHA-256 hash of the DER encoded certificate content.
    * If a client already has a certificate with this hash that was obtained from this publishing CA's certificate list,
    * it **MAY** skip downloading it again.
    */
    certificateHash OCTET STRING (SIZE(32)),
    /**
    * A public HTTPS URL where the X.509 certificate, encoded using ASN.1 DER, may be downloaded.
    * The data **SHALL** be presented with the `Content-Type` of `application/pkix-cert`.
    *
    * A client **SHALL** validate that the file it downloads calculates to the same SHA-256 hash as given above.
    */
    url             VisibleString
}

END
