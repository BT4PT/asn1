/**
* BT4PT Luggage Tag - DRAFT.
*/
BT4PT-LuggageTagV1-0 {
    iso(1) identified-organization(3) dod(6) internet(1) private(4) enterprise(1) uic(17218) fcb(1) bt4pt(2) luggageTag(12) v1(1) 0
} DEFINITIONS ::= BEGIN

EXPORTS LuggageTag, luggageTag;
IMPORTS GenericId, CompanyCode, Name, DATA-ELEMENT, Data, cuperEncoding, CompanyConstraint, DataAuthorization
 FROM BT4PT-GeneralElementsV1-0 { iso(1) identified-organization(3) dod(6) internet(1) private(4) enterprise(1) uic(17218) fcb(1) bt4pt(2) general(1) v1(1) 0 };

/**
* This structure identifies a piece of luggage and its owner.
*
* This structure contains personal data of the owner of the luggage, as such it **SHOULD** be encrypted.
*/
LuggageTag ::= SEQUENCE {
    /**
    * The identifier of the piece of luggage, assigned by the issuer of the luggage tag.
    * It **SHALL** be unique among all luggage tags issued by that issuer, and **SHALL NOT** be reused for another 
    * piece of luggage. A transport document **MAY** refer to the luggage tag by this identifier, in the `registrationId` 
    * of a `RegisteredLuggage` entry (see [](#luggage-ticket-link)).
    */
    id                  GenericId,
    /**
    * The issuer of the luggage tag.
    *
    * This field **SHALL NOT** be set unless it is different from the Security Provider in the envelope.
    * This field **SHALL** be set if the envelope is unsigned.
    */
    issuer              CompanyCode                                     OPTIONAL,
    /**
    * The name of the owner of the luggage.
    * As the name is personal data, an issuer **SHOULD** omit it unless the luggage tag is carried within an
    * [Encrypted Data](#encrypted-data) element or the owner of the luggage has consented to its disclosure.
    */
    name                Name                                            OPTIONAL,
    /**
    * The telephone number of the owner of the luggage, as an international number per [](cite:e164), consisting
    * of the country code followed by the national significant number, without any international prefix nor the
    * leading `+`. For example, `447700900378` for a United Kingdom mobile number.
    */
    telephone           VisibleString (SIZE(1..15) ^ FROM ("0".."9"))   OPTIONAL,
    /**
    * The email address of the owner of the luggage. This field **SHALL** be an `addr-spec` per 
    * [](cite:rfc5322 "3.4.1"), which **MAY** contain non-ASCII characters as permitted by [](cite:rfc6531).
    * Implementations **SHALL** support such internationalised email addresses.
    */
    email               UTF8String                                      OPTIONAL,
    /**
    * The language that the owner of the luggage prefers to be spoken to in.
    * This field **SHALL** contain an [IANA language subtag](https://www.iana.org/assignments/language-subtag-registry/language-subtag-registry), per [](cite:bcp47).
    */
    preferredLanguage   VisibleString (SIZE(2) ^ FROM ("a".."z"))       OPTIONAL,
    /**
    * Extensions to the luggage tag, identified by their `format`. A `format` of the `!I` variant refers to the issuer 
    * of the luggage tag.
    *
    * A party processing a luggage tag **SHALL** ignore any extension whose `format` it does not recognise, unless that
    * extension is critical, in which case the envelope **SHALL** be rejected as specified in [](#luggage-processing).
    */
    extensions          SEQUENCE (SIZE(1..8)) OF Data{{LuggageTagExtensions}} (WITH COMPONENTS {
        ...,
        format (ALL EXCEPT ("!C" | "!P"))
    }) OPTIONAL
}

/**
* The constraints placed on the Luggage Tag data element by a Security Provider Data Authorisation record, validated as
* specified in [](#luggage-data-authorisation). If a member is not present, then there are no constraints on that value.
*/
LuggageTagConstraints ::= SEQUENCE {
    /**
    * The companies permitted as the issuer of the luggage tag.
    */
    issuer      CompanyConstraint                           OPTIONAL,
    /**
    * The extensions permitted in the luggage tag, and the constraints on them.
    */
    extensions  DataAuthorization{{LuggageTagExtensions}}   OPTIONAL
}

/**
* The Luggage Tag data element, encoded with the Canonical Unaligned Packed Encoding Rules.
*/
luggageTag DATA-ELEMENT ::= { LuggageTag IDENTIFIED BY "LUG1" ENCODED WITH cuperEncoding CONSTRAINED BY LuggageTagConstraints }

/**
* The extensions that can appear in a {@link LuggageTag}. No extensions are defined in this version of this document.
* Note: other data elements, not defined in this standard, are permitted to appear.
*/
LuggageTagExtensions DATA-ELEMENT ::= { ... }

END
