BT4PT-DynamicContentDataV1-0 {
    iso(1) identified-organization(3) dod(6) internet(1) private(4) enterprise(1) uic(17218) fcb(1) bt4pt(2) dcd(4) v1(1) 0
} DEFINITIONS ::= BEGIN

EXPORTS DynamicContent, dynamicContentData, dynamicContentDataAligned;
IMPORTS Timestamp, GeoCoordinate, Data, GenericId, DATA-ELEMENT, cuperEncoding, caperEncoding
 FROM BT4PT-GeneralElementsV1-0 { iso(1) identified-organization(3) dod(6) internet(1) private(4) enterprise(1) uic(17218) fcb(1) bt4pt(2) general(1) v1(1) 0 };

/**
* This structure carries data generated by the Presentment Device at the time it generates the device data of an
* envelope.
*
* All fields of this structure are generated by the Presentment Device. They are signed by the Presentment Device only
* when the envelope is device-bound, and are never signed by the Security Provider. This structure **MAY** be included
* in envelopes even when they are not device bound; in such cases, the device data is not signed.
*/
DynamicContent ::= SEQUENCE {
    /**
    * This field conveys an identifier of this instance of the device data. The Presentment Device **SHALL** generate a
    * new value each time it generates the device data of an envelope, and **SHALL NOT** use the same value for two instances.
    * The value **SHALL NOT** be derived from any persistent identifier of the traveller or of the Presentment Device.
    *
    * This field has no relation to any ticket identifier in any ticket control database.
    * This field **SHALL NOT** be used in assessing the validity of an envelope; it exists for debugging purposes.
    */
    id                  GenericId           OPTIONAL,

    /**
    * The identifier of the application on the Presentment Device that generated the device data, with values as
    * defined by the Security Provider. Values could include the identifier of the mobile application package,
    * e.g. `com.example.app`.
    *
    * This field **SHALL NOT** be used to decide whether to accept or reject an envelope.
    */
    mobileAppId         VisibleString       OPTIONAL,

    /**
    * The geographic position of the Presentment Device when the device data was generated, as determined by the
    * Presentment Device. This field **SHALL NOT** be included unless the traveller has consented to the disclosure of
    * their location. In a device-bound envelope, this field **SHALL NOT** be included if the position was determined
    * more than `deviceBinding.validityDuration` seconds before the `timestamp` of the device signed data.
    */
    location            GeoCoordinate       OPTIONAL,

    /**
    * Responses to challenges supplied by a Ticket Inspection Device.
    *
    * No challenge-response mechanism is defined in this version of this document, and a Presentment Device 
    * implementing only this document **SHALL** omit this field.
    *
    * A Ticket Inspection Device **SHALL** reject an envelope containing a critical response whose `format` it does 
    * not recognise, as specified in [](#dcd-processing).
    */
    responseToChallenge SEQUENCE (SIZE(1..8)) OF Data{{ResponsesToChallenge}} (WITH COMPONENTS {
        ...,
        format (ALL EXCEPT ("!I" | "!C" | "!P"))
    })  OPTIONAL,

    /**
    * Traceability information about the application on the Presentment Device that generated the device data, with 
    * values as defined by the Security Provider. Values could include the version string of the mobile application.
    *
    * This field **SHALL NOT** contain personal data of the traveller.
    * This field **SHALL NOT** be used in assessing the validity of an envelope; it exists for debugging purposes.
    */
    traceability        VisibleString       OPTIONAL
}

/**
* The Dynamic Content Data element, encoded with the Canonical Unaligned Packed Encoding Rules.
*/
dynamicContentData DATA-ELEMENT ::= { DynamicContent IDENTIFIED BY "DCD1" ENCODED WITH cuperEncoding CONSTRAINED BY NULL }
/**
* The Dynamic Content Data element, encoded with the Canonical Aligned Packed Encoding Rules. It is otherwise
* identical to {@link dynamicContentData}.
*/
dynamicContentDataAligned DATA-ELEMENT ::= { DynamicContent IDENTIFIED BY "DCD1A" ENCODED WITH caperEncoding CONSTRAINED BY NULL }

/**
* The responses to challenges that can appear in {@link DynamicContent}. No responses are defined in this version of
* this document.
*
* Note: other documents and parties can define entries in this object set.
*/
ResponsesToChallenge DATA-ELEMENT ::= { ... }

END
