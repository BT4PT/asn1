/**
* BT4PT Multi-Modal Ticket Data - DRAFT.
*/
BT4PT-MultiModalTicketDataV1-0 {
    iso(1) identified-organization(3) dod(6) internet(1) private(4) enterprise(1) uic(17218) fcb(1) bt4pt(2) mmtd(3) v1(1) 0
} DEFINITIONS ::= BEGIN

EXPORTS MultiModalTicket, multiModalTicketData;
IMPORTS GenericId, GenericCode, CODE-TABLE-IDENTIFIER, CompanyCode, Name, Station, StationSet, AreaSet, NUTSArea, LineId,
 TransportId, GeoPosition, CoachPlaces, Data, DATA-ELEMENT, cuperEncoding, rawEncoding, UnicodeText, Timestamp,
 SharedVehicleVariety, SharedVehiclePropulsionType, SharedVehicleReturnConstraint, CompanyConstraint, DataAuthorization
 FROM BT4PT-GeneralElementsV1-0 { iso(1) identified-organization(3) dod(6) internet(1) private(4) enterprise(1) uic(17218) fcb(1) bt4pt(2) general(1) v1(1) 0 };

/**
* MultiModalTicket is the basic entry point of the data structure.
* Its data include:
* - issuer information (this is the only mandatory information)
* - information on the travelers independent from the transport document
* - information on the group
* - the details of the transport document
* - information required for the control process
* - proprietary extensions
*/
MultiModalTicket ::= SEQUENCE {
    /**
    * Details about how this ticket was issued, and by whom.
    */
    issuingDetail         IssuingData,

    /**
    * Traveler data. This field **SHALL NOT** be present unless personal data about the travelers is needed and legally permitted.
    * The index of the sequence elements can be used to identify the traveler within other contexts (e.g. in assigned tariffs).
    */
    traveler              SEQUENCE OF Traveler                  OPTIONAL,

    /**
    * Group details. Present if the traveler is a member of a group, otherwise omitted.
    * If this field is set, all group members **SHALL** be travelling together.
    */
    groupDetails          GroupDetails                          OPTIONAL,

    /**
    * Data of the transport documents.
    * Only one element **SHOULD** be a transportProduct, the others being associated documents.
    * (e.g. associated commercial card, associated tokens, associated carCarriage, vouchers...)
    */
    transportDocument     SEQUENCE SIZE (1..16) OF DocumentData OPTIONAL,

    /**
    * Proprietary data defined bilaterally.
    */
    extensions            SEQUENCE (SIZE(1..8)) OF Data{{MultiModalTicketExtensions}} (WITH COMPONENTS {
        ...,
        format (ALL EXCEPT ("!C" | "!P"))
    }) OPTIONAL
}

MultiModalTicketExtensions DATA-ELEMENT ::= { ... }

/**
* If a member is not present, then there are no constraints on that value.
*/
MultiModalTicketConstraints ::= SEQUENCE {
    issuer                      CompanyConstraint                               OPTIONAL,
    securePaperTicket           SecurePaperTicket                               OPTIONAL,
    issuingExtensions           DataAuthorization{{IssuingDataExtensions}}      OPTIONAL,
    mandatoryOnlineValidation   BOOLEAN                                         DEFAULT FALSE,
    controlExtensions           DataAuthorization{{ControlDataExtensions}}      OPTIONAL,
    carriers                    CompanyConstraint                               OPTIONAL,
    /**
    * The service brands, per code list B.4.7009 of [](cite:tel-tsi-codes), on which tickets signed under the
    * certificate may permit travel.
    */
    serviceBrands               SEQUENCE OF INTEGER (1..32000)                  OPTIONAL,
    transportTypes              SEQUENCE (SIZE(1..31)) OF INTEGER (1..31)       OPTIONAL,
    products                    SEQUENCE (SIZE(1..32)) OF ProductRestriction    OPTIONAL,
    transportDocument           DocumentConstraints                             OPTIONAL
}

ProductRestriction ::= SEQUENCE {
    /**
    * Restriction on the product owner.
    */
    owner   CompanyConstraint,
    /**
    * Restriction on the exact product ID. If unset, any product of the owner is permitted.
    */
    id      SEQUENCE {
        id      GenericId,
        /**
        * Indication whether to match on the prefix, suffix, or the full product ID.
        */
        format  IdFormat        DEFAULT full
    } OPTIONAL
}

multiModalTicketData DATA-ELEMENT ::= { MultiModalTicket IDENTIFIED BY "MMT1" ENCODED WITH cuperEncoding CONSTRAINED BY MultiModalTicketConstraints }

/**
* This data structure encodes the information relating to the issuance of a ticket.
* It represents who issued it, when it was issued, how it was issued, and other associated such details.
*/
IssuingData ::= SEQUENCE {
    /**
    * The issuer of the content of the transport document.
    * This field **SHALL NOT** be set unless it is different from the Security Provider in the envelope.
    */
    issuer              CompanyCode                 OPTIONAL,

    /**
    * In cases of a ticket directly tied to a sale process, this **SHALL** be the time the process was completed to a state
    * sufficient to issue the ticket. This could be, for example, when payment was confirmed.
    *
    * In other cases, this is the generation time of the envelope.
    */
    issuedAt            Timestamp,

    /**
    * This field **SHALL** be TRUE when it is in a specimen ticket.
    * Such tickets **SHALL NOT** be accepted for travel.
    */
    specimen            BOOLEAN,

    /**
    * This field is used to control duplication of tickets by means of secure (non-copyable) paper.
    */
    securePaperTicket   SecurePaperTicket,

    /**
    * This field indicates the currency for any price information in this ticket.
    * It **SHALL** contain the [](cite:iso4217) numeric code for that currency.
    *
    * The default value for this field is the code for the Euro.
    */
    currency            INTEGER (0..999)              DEFAULT 978,

    /**
    * This field indicates the decimal places for any price information in this ticket.
    * That is, when this field is 0, the integer prices encoded are full units of the currency;
    * when it is 1, the integers encoded are tenths of the currency; when it is 2, hundredths; etc.
    *
    * The default value for this field is hundredths of the full unit, e.g. Euro cents.
    */
    currencyFract       INTEGER (0..3)                DEFAULT 2,

    /**
    * When a ticket is issued on board a transport (i.e. it isn't purchased ahead of time), this field **SHALL**
    * contain information about that transport.
    */
    issuedOnBoard       SEQUENCE {
        /**
        * The identifier of a specific journey.
        */
        transport   TransportId OPTIONAL,
        /**
        * The identifier of the general route.
        */
        line        LineId      OPTIONAL
    } OPTIONAL,

    /**
    * Optional information about how the ticket was sold.
    */
    retail              RetailInformation           OPTIONAL,

    /**
    * The language that the traveler / group of travelers prefer to be spoken to in.
    * This field **SHALL** contain an [IANA language subtag](https://www.iana.org/assignments/language-subtag-registry/language-subtag-registry), per [](cite:bcp47).
    */
    preferredLanguage   VisibleString (SIZE(2) ^ FROM ("a".."z"))  OPTIONAL,

    /**
    * Optional proprietary extension data, see [](#data-elements).
    */
    extensions          SEQUENCE (SIZE(1..8)) OF Data{{IssuingDataExtensions}} (WITH COMPONENTS {
        ...,
        format (ALL EXCEPT ("!C" | "!P"))
    }) OPTIONAL
}

IssuingDataExtensions DATA-ELEMENT ::= { ... }

/**
* This enumeration is used to indicate if a ticket was issued on secure paper to ensure the uniqueness of the ticket.
* The duplicate use of the ticket is in this case excluded through the use of secure paper.
*/
SecurePaperTicket ::= ENUMERATED {
    /**
    * The ticket was issued digitally, or on paper that isn't secure (e.g. standard A4 printer paper).
    */
    notOnSecurePaper                        (0),
    /**
    * The ticket was printed on secure paper.
    * It **SHALL NOT** be accepted for travel, except when presented on such paper.
    */
    onSecurePaper                           (1),
    /**
    * In addition to being printed on secure paper (per above), the ticket is only valid if additionally physically stamped (DE: Entwerten).
    * It **SHALL NOT** be accepted for travel, except when presented on secure paper and with a suitable stamp.
    */
    onSecurePaperValidationStampRequired    (2)
}

/**
* This data structure encodes information about the retail of a ticket, i.e. how it was sold.
*/
RetailInformation ::= SEQUENCE {
    /**
    * A unique identifier for the sale transaction that caused this ticket to be issued.
    * The value of this field **SHALL** be unique within the scope of a retailer's (or of the issuer's, where
    * `retailerId` is absent) company code.
    */
    saleId              GenericId,

    /**
    * The identifier of the company that is the retailer for this ticket.
    * A retailer is defined as per the definition in [](cite:iso24014-1).
    *
    * This field **SHALL NOT** be set unless it is different from the issuer.
    */
    retailerId            CompanyCode       OPTIONAL,

    /**
    * A retailer specific identifier of the server that sold the contract of carriage.
    */
    retailServerId        GenericId         OPTIONAL,

    /**
    * A retailer specific identifier of the ticket generation platform.
    * If omitted, identical to retailServerId.
    */
    retailGeneratorId     GenericId         OPTIONAL,

    /**
    * The channel through which the traveler was sold the ticket.
    */
    retailChannel         RetailChannel     OPTIONAL,

    /**
    * The type of equipment that distributed the ticket, as per the code table of the retailer.
    */
    retailEquipmentType   GenericId         OPTIONAL,

    /**
    * An identifier for the final distribution point of the ticket, as per the code table of the retailer.
    */
    retailPointId         GenericId         OPTIONAL,

    /**
    * Traceability information for this ticket.
    * Its value, format, and meaning is defined by the retailer.
    * It could contain, for example, the name and version of the ticketing software.
    */
    retailTraceability    VisibleString     OPTIONAL
}

/**
* The choice on the different transport documents that can be included in the bar code data:
*   - universal transport product
*   - voucher
*   - customer card (including bonus cards and reduction cards)
*   - parking ground tickets
*   - station access / station passage tickets
*   - delay confirmation
*   - token
*   - proprietary documents as an extension
*/
DocumentData ::= CHOICE {
    /**
    * Universal transport product.
    * Can be used for tickets (incl. FIP), passes, reservations, countermarks.
    */
    transportProduct               TransportProduct,

    /**
    * Voucher of monetary value.
    */
    voucher                        Voucher,

    /**
    * Simple customer card either to identify a customer and / or to provide reductions or loyalty.
    * For detailed or complex commercial cards (e.g. valid only on a specific OD), use transportProduct instead.
    */
    customerCard                   CustomerCard,

    /**
    * Standalone car parking slot.
    * For parking as a part of a more global journey, use transportProduct instead.
    */
    parkingGround                  ParkingGround,

    /**
    * Ticket to pass the gates at a station.
    */
    stationPassage                 StationPassage,

    /**
    * Delay confirmation.
    */
    delayConfirmation              DelayConfirmation,

    /**
    * Token (e.g. for ABT).
    */
    token                          Token,

    /**
    * Proprietary data defined bilaterally.
    */
    extension                      Data{{ProprietaryDocumentTypes}} (WITH COMPONENTS {
        ...,
        format (ALL EXCEPT ("!C" | "!P"))
    })
}

ProprietaryDocumentTypes DATA-ELEMENT ::= { ... }

/**
* If the relevant document type constraint is not present, the certificate is not permitted to issue such a document.
*/
DocumentConstraints ::= SEQUENCE {
    transportProduct    TransportProductConstraints                     OPTIONAL,
    voucher             VoucherConstraints                              OPTIONAL,
    customerCard        CustomerCardConstraints                         OPTIONAL,
    parking             ParkingConstraints                              OPTIONAL,
    stationPassage      StationPassageConstraints                       OPTIONAL,
    delayConfirmation   DelayConfirmationConstraints                    OPTIONAL,
    token               TokenConstraints                                OPTIONAL,
    proprietary         DataAuthorization{{ProprietaryDocumentTypes}}   OPTIONAL
}

/**
* Description of a transport product, which may be:
* - A 'ticket' allowing the use of a transportation service.
* - A 'reservation' assigning a place in a transport, but not allowing travel unless accompanied by a ticket.
* - A 'commercial card' granting benefits when purchasing a ticket.
* - A 'proprietary' product which is very specific, in case none of the above choices apply.
*
* The type of the product is indicated by `generalConditions.product`.
*/
TransportProduct ::= SEQUENCE {
    /**
    * Geographical validity of the transport product.
    * This validity is described through successive segments that make up the route.
    * Omitted if the transport product is a 'reservation' (the concerned segment or transport being described by `generalConditions.transportService.reservation`)
    */
    geoValidity                 SEQUENCE (SIZE (1..16)) OF GeoValiditySegment               OPTIONAL,

    /**
    * To be provided in case the return route differs.
    * Omitted if the transport product is a 'reservation'.
    */
    returnGeoValidity           SEQUENCE (SIZE (1..16)) OF GeoValiditySegment               OPTIONAL,

    /**
    * General data that applies to all segments of this transport product.
    * Mandatory if the transport product is a 'reservation' (this product being a reservation being described through this element).
    */
    generalData                 SegmentData                                                 OPTIONAL,

    /**
    * Data that applies to only certain segments of this transport product.
    * If a particular condition is defined in both the general and the general data,
    *  the one in specific data overrules the one in the general data.
    */
    segmentData                 SEQUENCE (SIZE (1..32)) OF SegmentData                      OPTIONAL,

    /**
    * Where multiple applicable elements reference conditions, all referenced conditions are cumulative
    *  and **SHALL** all be satisfied unless explicitly specified otherwise.
    */
    conditions                  SEQUENCE (SIZE (1..32)) OF Conditions                       OPTIONAL,

    /**
    * Proprietary data defined bilaterally.
    */
    extensions                  SEQUENCE (SIZE(1..8)) OF Data{{TransportProductExtensions}} OPTIONAL
} (
    (WITH COMPONENTS {
        ...,
        generalData (WITH COMPONENTS {
            ...,
            productVariety PRESENT,
            coveringArea PRESENT
        }) PRESENT
    } | WITH COMPONENTS {
        ...,
        segmentData PRESENT
    }) ^ (WITH COMPONENTS {
        ...,
        geoValidity PRESENT
    } | WITH COMPONENTS {
        ...,
        geoValidity ABSENT,
        generalData (WITH COMPONENTS {
            ...,
            transportService (WITH COMPONENTS {
                reservation PRESENT
            }) PRESENT
        }) PRESENT
    })
)

TransportProductExtensions DATA-ELEMENT ::= { ... }

TransportProductConstraints ::= SEQUENCE {
    varietyTicket           BOOLEAN                                                 DEFAULT FALSE,
    varietyReservation      BOOLEAN                                                 DEFAULT FALSE,
    varietyCommercialCard   BOOLEAN                                                 DEFAULT FALSE,
    varietyProprietary      BOOLEAN                                                 DEFAULT FALSE,
    /**
    * Every `coveringArea` asserted by the transport product **SHALL** be wholly contained within at least one area in `permittedArea`.
    */
    permittedArea           SEQUENCE OF NUTSArea                                    OPTIONAL,
    /**
    * Every `coveringNetwork` asserted by the transport product **SHALL** be in the `permittedNetwork` list.
    */
    permittedNetwork        SEQUENCE OF GenericCode{GenericId, {NetworkCodeTables}}   OPTIONAL,
    extensions              DataAuthorization{{TransportProductExtensions}}         OPTIONAL,
    conditionsExtension     DataAuthorization{{ConditionsExtensions}}               OPTIONAL
}

/**
* Specification of the geographical validity of one segment of the whole journey.
*/
GeoValiditySegment ::= SEQUENCE {
    /**
    * Human readable description of the segment.
    */
    description                     UnicodeText     OPTIONAL,

    /**
    * Geographical description of the segment.
    */
    validitySegment                 GeoValidity,

    /**
    * The specific data are in `TransportProduct.segmentData`. This list is 1 indexed.
    */
    appliedSegmentDataIndex        INTEGER (1..32) OPTIONAL
}

/**
* Specification of the geographical validity for a segment.
*/
GeoValidity ::= CHOICE {
    /**
    * A journey described by a series of routing points.
    * Can be as simple as origin/destination, or as complex as allowing multiple origins, multiple destinations, alternative routes, etc.
    */
    pointBased          PointBasedRoute,
    /**
    * Validity defined with areas/zones.
    */
    area                Area,
    /**
    * Set of authorized transport lines.
    */
    line                Line,
    /**
    * Area defined using geocoordinates.
    */
    polygon            Polygon,
    /**
    * Parking right (for a car, a bike...).
    */
    parking             Parking,
    /**
    * Access to a shared vehicle service.
    */
    sharedVehicle       SharedVehicle,
    /**
    * No specific geographic validity beyond the coveringArea, included carriers, and other conditions.
    */
    perConditions       NULL,
    /**
    * Specific proprietary geographical validity in case the above predefined types do not allow it to be described.
    */
    proprietary         Data{{GeoValidityExtensions}}
}

GeoValidityExtensions DATA-ELEMENT ::= { ... }

/**
* Includes a description of the route by via stations.
* Via stations follow the description in leaflet 108.1:
* - Via stations can be mandatory to pass, but there does not need to be a
*     stop at these stations: visible route description: "*station*"
* - There can be a list of alternative routes:
*     visible route description: "*(station1/station2)*"
* - There can also be alternative routes: "*(station1*station2/station3*station4)*"
*     although the definition in 108.2 is not very precise on this option
*/
PointBasedRoute ::= SEQUENCE {
    routeItem                       SEQUENCE OF RouteItem,

    /**
    * In case different break of service allowances, different carriers, different service brands, etc.
    * need to be indicated on the routes or alternative routes.
    * Index into `TransportProduct.conditions`.
    * The first element has index 1.
    */
    appliedConditionsIndex          INTEGER (1..32)        OPTIONAL
}

RouteItem ::= CHOICE {
    /**
    * The route item is the destination station from the previous `GeoValiditySegment` (**not** the previous `PointBasedRoute`).
    */
    destinationStationOfPreviousSegment NULL,

    /**
    * The route item is a specific station.
    */
    station                             Station,

    /**
    * The route item is a set of stations that are equivalent (OSDM: FareStationSet).
    */
    stationSet                          StationSet,

    /**
    * The route item is any point that is within at least one of the specified areas.
    */
    area                                AreaSet,

    /**
    * In case conditions/break of journey restrictions need to be applied only to part of a route.
    */
    route                               PointBasedRoute,

    /**
    * A list of alternative routes - one, and only one, of these has to be taken.
    */
    alternativeRoutes                   SEQUENCE OF PointBasedRoute
}

/**
* Geographical validity defined with areas/zones.
*/
Area ::= SEQUENCE {
    /**
    * Description of the allowed areas/zones.
    * The areas described in `restrictedEntry:area` and/or `restrictedExit:area` (if any) must not be repeated in the included or excluded areas.
    * If `restrictedEntry` is absent, the journey can begin anywhere in the allowed areas/zones.
    * If `restrictedExit` is absent, the journey can end anywhere in the allowed areas/zones.
    * If `restrictedEntry` and `restrictedExit` and area are present, the allowed areas/zones are only transit areas/zones:
    *  the traveler is allowed to cross them, but may neither begin nor end their journey in them.
    * If `restrictedEntry` and `restrictedExit` are present, and area is absent, there are no specific restrictions on how to travel
    *  from `restrictedEntry` to `restrictedExit` (the only restrictions that apply are those described by the applicable `Conditions`).
    */
    area CHOICE {
       /**
       * The allowed areas/zones are those explicitly described in this field.
       */
       included AreaSet,

       /**
       * The allowed areas/zones are all the areas/zones of the applicable `coveringArea` element, except those
       *  described in this element, in `restrictedEntry` and in `restrictedExit`.
       */
       excluded AreaSet
    } OPTIONAL,

    /**
    * Readable name of the area of validity.
    */
    areaNameUTF8    UnicodeText OPTIONAL
}

/**
* Geographical validity using a set of lines
*/
Line ::= SEQUENCE {
    lineIds             CHOICE {
        included    SEQUENCE OF LineId,
        excluded    SEQUENCE OF LineId
    },

    /**
    * In case the line must be entered via a specific station.
    */
    entryStation        StationSet  OPTIONAL,

    /**
    * In case the line must be left via a specific station.
    */
    terminatingStation  StationSet  OPTIONAL
}

/**
* Geographical validity defined as a polygon.
*/
Polygon ::= SEQUENCE {
    edges         SEQUENCE OF GeoPosition
}

/**
* Access to a shared vehicle service, e.g. car sharing or bike/e-scooter rental
*/
SharedVehicle ::= SEQUENCE {
    /**
    * Shared vehicle providers that this entitlement covers
    */
    carriers            SEQUENCE OF CompanyCode,

    /**
    * The number of individual vehicles included in this entitlement
    */
    numberOfVehicles    INTEGER (1..16)             DEFAULT 1,

    /**
    * Which kinds of shared vehicles are included in this entitlement
    * An empty list means no constraint.
    */
    vehicleTypes        SEQUENCE OF SharedVehicleType,

    /**
    * The vehicle must be collected from this station.
    */
    collectionStation   Station                     OPTIONAL,
    /**
    * The vehicle must be returned to this station.
    */
    returnStation       Station                     OPTIONAL,

    /**
    * Included amount of time allowed to access a shared vehicle, if more restrictive than the validity period.
    * If present, indicates that the entitlement is valid for a given amount of time within the validity period.
    * If present, the count of the remaining number of allowed days or minutes is centrally held in a back office,
    *  that **SHALL** be queried to verify whether the traveler still has any remaining time.
    * Whether an operator allows the traveler to pay additionally for more time once the allotted time is up is
    * per local operator policy.
    */
    allowedTime         CHOICE {
        days    INTEGER,
        minutes INTEGER (1..1439)
    }                                               OPTIONAL,

    /**
    * Additional readable information that cannot be described using the other elements.
    */
    infoText            UnicodeText                 OPTIONAL,

    -- Proprietary data defined bilaterally.
    extensions      SEQUENCE (SIZE(1..8)) OF Data{{SharedVehicleExtensions}} OPTIONAL
}

SharedVehicleExtensions DATA-ELEMENT ::= { ... }

SharedVehicleType ::= SEQUENCE {
    /**
    * An empty list means any value.
    */
    variety             SEQUENCE SIZE (0..15) OF SharedVehicleVariety,
    /**
    * An empty list means any value.
    */
    propulsion          SEQUENCE SIZE (0..15) OF SharedVehiclePropulsionType,
    /**
    * An empty list means any value.
    */
    returnConstraint    SEQUENCE SIZE (0..15) OF SharedVehicleReturnConstraint
}

/**
* Information about each segment of the transport product.
* - if used for `generalData`: applies to the entire transport product.
* - if used for `segmentData`: applies to the associated segment.
*/
SegmentData ::= SEQUENCE {
    /**
    * Detailed type of the transport product (ticket, reservation, commercial card...).
    * Each GeoValiditySegment **SHALL** have a set `productVariety`, either through the `generalData` or a referenced
    *  `segmentData`.
    */
    productVariety                  ProductVariety                                          OPTIONAL,

    /**
    * NUTS codes covering the whole area of validity of the ticket.
    * This does not mean that the ticket is valid everywhere inside such areas, but that it definitely
    *  is NOT valid outside the covering area.
    * Each GeoValiditySegment **SHALL** have a set `coveringArea`, either through the `generalData` or a referenced
    *  `segmentData`. Tickets without a coveringArea on every segment **SHALL** be rejected as malformed tickets.
    * Validity to specific services, transport modes, etc., may be further constrained by other conditions.
    * Examples:
    *   - An international ticket from Munich to Vienna has the covering areas of `DE` and `AT`
    *   - A ticket valid on buses in the Saarland has a covering area of `DEC`
    *   - A ticket valid on the tram in Kehl and Strasbourg has the covering areas of `DE134` (Ortenaukreis) and `FRF11` (Bas-Rhin)
    *       n.b. a NUTS Local Administrative Units (LAU) could be further appended, e.g. `DE13408317057` for Kehl, Stadt.
    *
    * When comparing, the ticket validator compares the covering area of the service the ticket is being validated on
    * (service area) with each covering area element in the ticket, truncating both to the shortest of either.
    * For example, with a service area `DE2` (a service running in Bavaria), `DE` (all of Germany) and `DE212` (Munich)
    * match, but `DE3` (Berlin) does not.
    */
    coveringArea                    SEQUENCE OF NUTSArea                                    OPTIONAL,

    /**
    * Once a validator narrowed down the possibly valid geographic segments it **MAY** further narrow down segments
    *  by using the coveringNetwork field.
    * This encodes the IDs of transport networks that COULD be involved in the fulfillment of transport contract.
    * There is no requirement to use this field if the coveringArea adequately narrows down the possibly valid segments.
    * Examples:
    *   - In France, the codeTable of national can be used to refer to an Afnor network/region ID, e.g. to refer to the
    *      Maconnais Beaujolais Agglomération: `{ codeTable national : 250, id idNum : 145 }`
    */
    coveringNetwork                 SEQUENCE OF GenericCode{GenericId, {NetworkCodeTables}}   OPTIONAL,

    /**
    * Identification of the product (owner, id, textual description).
    */
    product                         Product                                                 OPTIONAL,
    /**
    * Family of the product, allowing to process the product according to its family.
    * Value according to the product owner.
    */
    productFamily                   GenericId                                               OPTIONAL,

    /**
    * `TRUE` if the direction of travel must be followed as described:
    *  - in `generalData`: the traveler must pass the sequence of segments in the provided order
    *     (but some segments may be skipped, e.g. if 2 segments are 2 allowed alternatives for the same journey).
    *  - in `segmentData`: the traveler must take the transport in the direction indicated by the segment (e.g. from O to D).
    *
    * `FALSE` if the direction of travel is not mandatory:
    *  - in `generalData`: the traveler can travel through the described segments in any order.
    *  - in `segmentData`: the traveler can take the transport indicated by the segment in any direction (e.g. from O to D or from D to O).
    *
    * Omitted if the concept of direction is not relevant (e.g. for geographical validity as unordered areas).
    */
    directionIsMandatory            BOOLEAN                                                 OPTIONAL,

    /**
    * Link to a specific transport services.
    * Note that for a return ticket where the outbound and inbound geographic validates are the same, and thus the
    * returnGeoValidity is not encoded, this field encodes linked transport services for both the outbound and
    * inbound directions.
    */
    transportService CHOICE {
        /**
        * Link to a specific transport service without reservation.
        * If present, using this transport service is mandatory.
        */
        transportLink               SEQUENCE OF TransportLink,

        /**
        * Link to a specific transport service with reservation.
        * A reservation does not mandate taking the reserved service.
        */
        reservation                 SEQUENCE OF ReservationSegment
    } OPTIONAL,

    /**
    * Tariff data (allowed passengers characteristics, discount cards used...)
    * If omitted, the ticket is valid:
    *  - for all of the travelers described in the `traveler` section if this section is present,
    *  - for one passenger (without any further information) if the `traveler` section is absent.
    */
    tariff                          SEQUENCE OF Tariff                                      OPTIONAL,

    /**
    * Specific data to support the ticket inspection process.
    */
    controlData                     ControlData                                             OPTIONAL,

    /**
    * Associated online identifier (e.g. Account Based Ticketing identifier).
    */
    token                           Token                                                   OPTIONAL,

    activation                      Activation                                              OPTIONAL,

    /**
    * Index into `TransportProduct.conditions`.
    * The first element has index 1.
    */
    appliedConditionsIndex          INTEGER (1..32)                                         OPTIONAL
}

NetworkCodeTables CODE-TABLE-IDENTIFIER ::= {
    /**
    * As defined in NF P99-502 NAO (France).
    */
    {&table {
        owner national : 250,
        version 0
    }},
    ...
}

/**
* Data supporting the control process, whether it is an automatic check carried out by a gate, or a manual check
* carried out by an inspector.
*/
ControlData ::= SEQUENCE {
    /**
    * ID to uniquely identify this barcode within the context of the issuer and an appropriate time range.
    * This can be used to query the ticket in the eTCD.
    */
    ticketControlNumber         GenericId,
    /**
    * Indicator of whether online validation of the ticket is required.
    */
    onlineValidationRequired    OnlineValidationStatus      DEFAULT notPossible,
    /**
    * Indicator of how online validation may be performed.
    */
    onlineValidationType        OnlineValidationType        OPTIONAL,

    /**
    * Indicator of whether ID must be checked to identify the traveler.
    * Field meaning:
    * - `FALSE`: don’t check ID documents at all, regardless of contents of the traveler's identificationDocument field.
    * - `TRUE`, but with an empty identificationDocument field: check the traveler's identity, using whatever document is acceptable to the carrier.
    * - `TRUE`, with an identificationDocument field: check the traveler's identity, using the identification document specified.
    */
    identificationRequired      BOOLEAN                     DEFAULT FALSE,

    /**
    * Indicator of whether validation of the traveler age is required (e.g. in case of reductions).
    */
    ageCheckRequired            BOOLEAN                     DEFAULT FALSE,

    /**
    * Indicator of whether validation of the travelers reduction card is required (e.g. in case of reductions).
    */
    reductionCardCheckRequired  BOOLEAN                     DEFAULT FALSE,

    /**
    * Tickets, that are not encoded in this ticket, which need to be controlled together with this ticket to form a valid ticket.
    */
    linkedTickets               SEQUENCE OF TicketLink      OPTIONAL,

    /**
    * Free text instructions for specific control instructions to be presented to the ticket controller where these
    *  instructions can't be expressed in structured data, e.g. "Verify no more than two people over 18" on a family group ticket.
    */
    infoText                    UnicodeText                 OPTIONAL,

    /**
    * Proprietary data defined bilaterally.
    */
    extensions                  SEQUENCE (SIZE(1..8)) OF Data{{ControlDataExtensions}} (WITH COMPONENTS {
        ...,
        format (ALL EXCEPT ("!C" | "!P"))
    }) OPTIONAL
}

ControlDataExtensions DATA-ELEMENT ::= { ... }

OnlineValidationStatus ::= ENUMERATED {
    /**
    * No information is available online so it is useless to check.
    */
    notPossible (1),
    /**
    * The ticket can be fully validated and checked offline, i.e. the ticket contains all the information necessary
    * for validation and inspection and is therefore self-sufficient, but some operators, in an interoperability
    * scenario, nevertheless choose to operate this ticket in ABT mode and validate it online.
    */
    optional    (2),
    /**
    * Online operations **SHALL** be performed to validate or check this ticket, e.g.:
    * - For a Pay-as-you-go ticket, check during inspection that it has been validated.
    * - For a ticket valid for 3 hours from the first validation, check when this first validation took place.
    * - For a fully ABT (Account Based Ticketing) document: check the details of the ticket in the ABT account (whose ID may be specified in 'token').
    * - For a ticket authorizing a limited number of trips: check how many trips have already been made.
    * - For a ticket that can be refunded until the last moment: check if the ticket has been cancelled and refunded.
    */
    mandatory   (3)
}

OnlineValidationType ::= CHOICE {
    /**
    * The ticket may be checked against the UIC's eTCD.
    */
    eTCD                        NULL,
    /**
    * The ticket may be checked against a proprietary platform of the security provider; e.g. the Deutschlandtarifverbund's security portal.
    */
    securityProviderProprietary NULL,
    /**
    * The ticket may be checked against a proprietary platform of the issuer; e.g. bwegt check-in check-out (Baden-Württemberg).
    */
    issuerProprietary           NULL,
    /**
    * The ticket may be checked against the platform operated by the specified company; e.g. Entur.
    */
    external                    CompanyCode,

    /**
    * The ticket may be checked against some other external platform, as identified by the string. It can be of the following forms:
    * - `+` + [2-letters uppercase ISO 3166 country code] + [addon, chosen by the national standards body of that country]
    * - `_` + [RICS or ERA Organisation Code] + [addon, chosen by this company]
    * - `!I` + [addon, chosen by the issuer] - equivalent to the _RICS format, without repetition of the issuer's code.
    * - `!C` + [addon, chosen by the carrier] - equivalent to the _RICS format, without repetition of the carriers' code.
    * - `!P` + [addon, chosen by the product owner] - equivalent to the _RICS format, without repetition of the product owner's code.
    * - `*` + [addon] - private use, not guaranteed to avoid clashes.
    *
    * Any other value only after registration in the appropriate registry.
    * Unregistered values (outside of the national, company, and private use ranges) **SHALL NOT** be used.
    * If an organisation has a RICS or an ERA Organisation Code the private use format **SHALL NOT** be used.
    * All values **SHOULD** be registered via the UIC Github repository.
    */
    other                       ONLINE-VALIDATION-METHOD.&id({OnlineValidationMethods})
}

ONLINE-VALIDATION-METHOD ::= CLASS {
    &id VisibleString (SIZE(1..8)) UNIQUE,
    &name UTF8String
} WITH SYNTAX {
    &id MEANING &name
}

OnlineValidationMethods ONLINE-VALIDATION-METHOD ::= { ... }

Activation ::= SEQUENCE {
    /**
    * List of activated days in case the entire ticket is not activated.
    * The ticket can only be used on the days it is activated.
    * If the ticket is a return ticket, activatedDay only applies to the outward journey (use activatedReturnDay for the return journey).
    * Each day is given by the number of days from the first day of validity (validFrom) (0 = first day of validity).
    * For each day that the ticket is activated, the activation is valid from 00:00 to 23:59 in the time zone of the traveler's current location,
    * thereby the activation might include more or less than 24 hours in case time zone borders are crossed.
    * Travel days of a ticket might be subject to a separate activation to be valid for traveling.
    * Omitted if there are no restrictions on days of use between `validFrom` and `validUntil`.
    */
    activatedDay                            SEQUENCE (SIZE(1..501)) OF INTEGER (0..500)      OPTIONAL,

    /**
    * In case of a return ticket only: list of activated days for the return journey.
    * Same use as `activatedDay` but for the return journey
    * Omitted if there are no restrictions on days of use between `validFrom` and `validUntil` for the return journey.
    */
    activatedReturnDay                      SEQUENCE (SIZE(1..501)) OF INTEGER (0..500)     OPTIONAL
}

/**
* Information about the validity conditions of a whole transport product, a segment thereof, or a specific tariff.
*/
Conditions ::= SEQUENCE {
    /**
    * Having no `validFrom` is allowed (e.g. ticket not yet activated, which will be reissued with an explicit `validFrom` upon activation).
    * Having no `validUntil` is allowed (e.g. ticket with unlimited validity - which should nevertheless have a security expiry date in the header requiring regular reissue).
    */
    validFrom                       ValidFrom                                               OPTIONAL,
    validUntil                      ValidUntil                                              OPTIONAL,
    rareTimingConditions            RareTimingConditions                                    OPTIONAL,

    /**
    * Whether the traveler may voluntarily interrupt the journey and continue it later.
    *
    * This does not restrict changes between transport services that are necessary to continue the journey.
    */
    breakOfJourney                  BOOLEAN                                                 DEFAULT TRUE,

    /**
    * Carriers/modes of transport included in this ticket.
    */
    includedServiceVarieties        SEQUENCE OF TransportVariety                            OPTIONAL,
    /**
    * Carriers/modes of transport excluded from this ticket.
    * In case `includedServiceVarieties` is not provided, the ticket is valid on all services in its
    * `coveringArea` and `coveringNetwork`, except those in this field.
    * If `includedServiceVarieties` is specified, then the exclusions are processed logically after any inclusions.
    * That is, even if the ticket conditions include a service, an exclusion overrides that.
    */
    excludedServiceVarieties        SEQUENCE OF TransportVariety                            OPTIONAL,

    /**
    * Travel class.
    * For transport modes where the concept of class does not exist, this field **SHALL** be set to `notApplicable`.
    */
    classCode                       TravelClass                                             DEFAULT second,

    /**
    * Per code list B.5.308 of [](cite:tel-tsi-codes).
    */
    fareCode                        VisibleString (SIZE(1..2) ^ FROM ("A".."Z"|"0".."9"))   OPTIONAL,

    /**
    * Reduction cards applied (incl. discount cards, loyalty cards relevant for the tariff).
    * To require verification of these cards during an inspection, use `ControlData.reductionCardCheckRequired`.
    * Omitted if these cards have already been verified at the time of purchase and their verification is not requested during inspection.
    */
    reductionCard                   SEQUENCE (SIZE(1..16)) OF CardReference                 OPTIONAL,

    rareDetails                     RareDetails                                             OPTIONAL
}

/**
* An identifier for the variety of transport included in/excluded from ticket conditions.
* The fields in this SEQUENCE are to be ANDed together as part of matching.
* That is, if ticket includes a transport variety with both `carrier eraCode : "1080"` and `transportType 10` set,
* then it is only valid on high-speed trains operated by the Deutsche Bahn.
*/
TransportVariety ::= SEQUENCE {
    carrier         CompanyCode         OPTIONAL,
    /**
    * Per EN 1545-1 (transport type code).
    */
    transportType   INTEGER (1..31)     OPTIONAL,
    /**
    * Per code list B.4.7009 of [](cite:tel-tsi-codes).
    */
    serviceBrand    INTEGER (1..32000)  OPTIONAL
}

/**
* Rare temporal details and conditions.
*/
RareTimingConditions ::= SEQUENCE {
    /**
    * Extended validity for tickets valid up to just over 5 years.
    * If this element is used, the eponymous element in `Conditions` **SHALL NOT** be used.
    * For security reasons, such a long lasting ticket should:
    *  - either have a shorter security expiry date set in the header and be regularly reissued,
    *  - or integrate other countermeasures such as Security In Paper and/or the use of a dedicated key.
    */
    validUntil                              ExtendedValidUntil                              OPTIONAL,

    /**
    * Offset in units of 15 minutes from local time to UTC (UTC = local + offset * 15 Minutes).
    * The UTC offset can be used to calculate the duration of the travel.
    * If UTC offset is used in control devices the usage of UTC offset has to be agreed bilateral to be mandatory.
    * Times to be shown on a ticket should always be the local times.
    */
    validFromUTCOffset                       INTEGER (-60..60)                              OPTIONAL,

    /**
    * Offset in units of 15 minutes from local time to UTC (UTC = local + offset * 15 Minutes).
    * The UTC offset can be used to calculate the duration of the travel.
    * If UTC offset is used in control devices the usage of UTC offset has to be agreed bilateral to be mandatory.
    * Times to be shown on a ticket should always be the local times.
    * Omitted in case it is the same as `validFromUTCOffset`.
    */
    validUntilUTCOffset                      INTEGER (-60..60)                              OPTIONAL,

    /**
    * In case included time ranges are defined, the validity is restricted to these ranges.
    */
    includedTimeRanges                       SEQUENCE OF IncludedTimeRanges                 OPTIONAL,

    /**
    * Proprietary data defined bilaterally.
    */
    extensions                              SEQUENCE (SIZE(1..8)) OF Data{{TimingExtensions}} OPTIONAL
}

TimingExtensions DATA-ELEMENT ::= { ... }

/**
* Rare non-temporal details and conditions.
*/
RareDetails ::= SEQUENCE {
    /**
    * Price of the transport product (if in `generalConditions`) or of the segment (if in `specificConditions`),
    *   in the currency and fraction defined in IssuingData.
    */
    price                       INTEGER                                             OPTIONAL,

    /**
    * To be used in case of special conditions that can only be provided as a readable text, e.g. that Interrail
    *   is valid on a night train continuing into the following day.
    * For specific control instructions that should be brought to the attention of the ticket checker,
    *   use `ControlData.infoText`.
    */
    conditionText               UnicodeText                                         OPTIONAL,

    /**
    * In case the luggage restrictions are general and do not depend on the ticket type they should not be included.
    */
    luggage                     LuggageRestriction                                  OPTIONAL,

    /**
    * Validity restriction based on the traveler's country of residence.
    * (e.g. for Eurail tickets that are not valid in the country of residence).
    * This field does not indicate a global geographic validity, but only a possible
    * restriction of this geographic validity related to the country of residence.
    * Omitted if there is no restriction related to the traveler's country of residence.
    */
    countryValidity             CountryValidity                                     OPTIONAL,

    /**
    * Proprietary data defined bilaterally.
    */
    extensions                  SEQUENCE (SIZE(1..8)) OF Data{{ConditionsExtensions}}   OPTIONAL
}

ConditionsExtensions DATA-ELEMENT ::= { ... }

/**
* Information for linking a car to a reservation
*/
Car ::= SEQUENCE {
    /**
    * Unless spaces form an integral part of identifying a plate, they **SHALL NOT** be included.
    * E.g. a German car with the plate SB[TÜV Sticker]A 123 **SHALL** be encoded as `SB-A123`.
    * Dutch duplicate codes **SHALL NOT** be encoded, i.e. the small number above the first dash does not
    * form part of the plate.
    *
    * The plate **SHOULD** be represented in the Latin alphabet and Arabic numerals where possible,
    * but note that this isn't always possible, e.g. the registration district of a Chinese plate.
    *
    * The country of registration **SHALL NOT** be encoded in the plate.
    */
    vehiclePlate        UnicodeText,
    trailerPlate        UnicodeText         OPTIONAL,
    /**
    * Per code list B.5.29 of [](cite:tel-tsi-codes).
    */
    carCategory         INTEGER (1..8),
    /**
    * Per code list B.5.29 of [](cite:tel-tsi-codes).
    */
    boatCategory        INTEGER (1..8)      OPTIONAL,
    textileRoof         BOOLEAN,
    roofRack            RoofRack            DEFAULT  norack,

    /**
    * Height of a roof rack in cm.
    */
    roofRackHeight      INTEGER (0..99)     OPTIONAL,

    /**
    * Number of boats on a rack.
    */
    attachedBoats       INTEGER (0..2)      OPTIONAL,

    /**
    * Number of bicycles on a rack.
    */
    attachedBicycles    INTEGER (0..4)      OPTIONAL,

    /**
    * Number of surf boards on a rack.
    */
    attachedSurfboards  INTEGER (0..5)      OPTIONAL,

    /**
    * Reference to an entry on the loading list.
    */
    loadingListEntry    INTEGER (0..999)    OPTIONAL,
    loadingDeck         LoadingDeck         OPTIONAL,

    /**
    * Loading of the car in local date and time at the loading station.
    * Number of the days calculated from the issuing date.
    */
    beginLoading        ValidFrom,
    endLoading          ValidUntil          OPTIONAL
}

/**
* Type definitions used in `TransportLink` and `ReservationSegment`.
*/
DepartureDateTime ::= SEQUENCE {
    /**
    * Departure date and time in local time at the departure station.
    * Number of days counted from the issuing date.
    */
    departureDate      INTEGER (-1..500)                DEFAULT 0,
    departureTime      INTEGER (0..1439),

    /**
    * Offset in units of 15 minutes from local time to UTC
    * (UTC = local + offset * 15 minutes).
    * The UTC offset can be used to calculate the duration of the travel.
    * Times to be shown on a ticket should always be the local times.
    */
    departureUTCOffset INTEGER (-60..60)                OPTIONAL
}

DepartureWindow ::= SEQUENCE {
    /**
    * The date and time the departure window begins at.
    */
    startOfWindow       DepartureDateTime,
    /**
    * How many full days onwards from the start of the window does it continue.
    */
    windowLengthDays    INTEGER (0..30)     DEFAULT 0,
    /**
    * How many minutes onwards from the start of the window does it continue.
    */
    windowLengthMinutes INTEGER (0..1439)
}

ArrivalDateTime ::= SEQUENCE {
    /**
    * Arrival date and time in local time at the arrival station.
    * Number of days counted from the departure date.
    */
    arrivalDate        INTEGER (-1..30)                 DEFAULT 0,
    arrivalTime        INTEGER (0..1439)                OPTIONAL,

    /**
    * Offset in units of 15 minutes from local time to UTC
    * (UTC = local + offset * 15 minutes).
    * Should be omitted in case it is the same as for departure.
    * The UTC offset can be used to calculate the duration of the travel.
    * Times to be shown on a ticket should always be the local times.
    */
    arrivalUTCOffset   INTEGER (-60..60)                OPTIONAL
}

ArrivalWindow ::= SEQUENCE {
    /**
    * The date and time the arrival window begins at.
    */
    startOfWindow       ArrivalDateTime,
    /**
    * How many full days onwards from the start of the window does it continue.
    */
    windowLengthDays    INTEGER (0..30)     DEFAULT 0,
    /**
    * How many minutes onwards from the start of the window does it continue.
    */
    windowLengthMinutes INTEGER (0..1439)
}

/**
* Describes a transport link associated to a route or to a part of a route.
* Quite similar to ReservationSegment but without assigned place(s).
*/
TransportLink ::= SEQUENCE {
    /**
    * Station where the transport link begins.
    * Omitted if it is the same station as the origin station of the associated segment.
    */
    originStation           Station                                                 OPTIONAL,

    /**
    * Station where the transport link ends.
    * Omitted if it is the same station as the destination station of the associated segment.
    */
    destinationStation      Station                                                 OPTIONAL,

    /**
    * Transport numbers (= service number, train number) allowed for the transport link.
    * Multiple numbers are allowed (e.g. two trains coupled together, each of them having its own train number).
    */
    transportNumber         SEQUENCE (SIZE(1..8)) OF TransportId                    OPTIONAL,

    /**
    * Departure date and time in local time at the departure station of the transport link.
    * If omitted, it is assumed to be equal to validFrom and validFromUTCOffset of the container object.
    */
    departure               CHOICE {
        /**
        * A transport service departing at exactly a date and time, i.e. a link to one service.
        */
        exact   DepartureDateTime,
        /**
        * A window of time in which the transport must depart the origin, e.g. the traveler must take a service
        * departing within 60-minute time window.
        */
        window  DepartureWindow
    } OPTIONAL,

    /**
    * Arrival date time in local time at the arrival station of the transport link.
    * If omitted, arrivalDateTime is assumed to be equal to validUntil and validUntilUTCOffset of the container object.
    */
    arrival               CHOICE {
        /**
        * A transport service arriving at exactly a date and time, i.e. a link to one service.
        */
        exact   ArrivalDateTime,
        /**
        * A window of time in which the transport must arrive at the destination, e.g. the traveler must take a service
        * arriving within 60-minute time window.
        */
        window  ArrivalWindow
    } OPTIONAL,

    /**
    * Travel class.
    * For transport modes where the concept of class does not exist, this field **SHALL** be set to notApplicable.
    * Omitted if the class is the same as the class of the associated leg.
    */
    classCode               TravelClass                                             DEFAULT second,

    /**
    * Service brand.
    * Omitted if this specific service brand is already specified in the associated leg, and is the only one that is specified for this leg
    * (a leg can allow many service brands, but a transport link only specifies one).
    * Per code list B.4.7009 of [](cite:tel-tsi-codes).
    */
    serviceBrand            INTEGER (1..32000)                                       OPTIONAL,

    /**
    * Per code list B.5.308 of [](cite:tel-tsi-codes).
    * Omitted if the same fare code is already specified in the description of the associated leg.
    */
    fareCode                VisibleString (SIZE(1..2) ^ FROM ("A".."Z"|"0".."9"))   OPTIONAL
}

/**
* Describes a reservation associated to a route, or to a part of a route.
* Usable for a standalone reservation and for a reservation linked to a leg.
*/
ReservationSegment ::= SEQUENCE {
    /**
    * `TRUE` if using this transport service is mandatory.
    * `FALSE` if the traveler can use another transport service.
    */
    mandatoryService        BOOLEAN                                                 DEFAULT TRUE,

    /**
    * Station where the reservation begins.
    * Omitted if it is the same station as the origin station of the associated segment.
    */
    originStation           Station                                                 OPTIONAL,

    /**
    * Station where the reservation ends.
    * Omitted if it is the same station as the destination station of the associated segment.
    */
    destinationStation      Station                                                 OPTIONAL,

    /**
    * Transport number (=service number, train number).
    */
    transportNumber         TransportId                                             OPTIONAL,

    /**
    * Departure date and time in local time at the departure station.
    * If omitted, departureDateTime is assumed to be equal to `validFrom` and `validFromUTCOffset` of the container object.
    */
    departureDateTime       DepartureDateTime                                       OPTIONAL,

    /**
    * Arrival date time in local time at the arrival station.
    * If omitted, arrivalDateTime is assumed to be equal to `validUntil` and `validUntilUTCOffset` of the container object.
    */
    arrivalDateTime         ArrivalDateTime                                         OPTIONAL,

    /**
    * For transport modes where the concept of class does not exist, this field **SHALL** be set to notApplicable.
    * Omitted if the class is the same as the class of the associated leg.
    */
    classCode               TravelClass                                             DEFAULT second,

    /**
    * Omitted if this specific service brand is already specified in the associated leg, and is the only one that is specified for this leg
    * (a leg can allow many service brands, but a reservation only specifies one).
    * Per code list B.4.7009 of [](cite:tel-tsi-codes).
    */
    serviceBrand            INTEGER (1..32000)                                       OPTIONAL,

    /**
    * Per code list B.5.308 of [](cite:tel-tsi-codes).
    * Omitted if the same fare code is already specified in the description of the associated leg.
    */
    fareCode                VisibleString (SIZE(1..2) ^ FROM ("A".."Z"|"0".."9"))   OPTIONAL,

    /**
    * Per [](cite:tel-tsi-b5).
    */
    service                 ServiceType                                             DEFAULT seat,

    /**
    * Reserved places.
    */
    coachPlaces             SEQUENCE OF CoachPlaces                                 OPTIONAL,

    /**
    * Number of persons on the ticket having a reservation without assigned places.
    */
    numberOfOverbooked      INTEGER (1..200)                                        OPTIONAL,

    /**
    * Description of berths.
    */
    berth                   SEQUENCE OF BerthDetailData                             OPTIONAL,

	/**
	* When a reservation includes transportation of a car, this field is used to include details of the booked car or cars.
	*/
	cars					SEQUENCE OF Car                                         OPTIONAL
}

/**
* Data for groups of travelers
*/
GroupDetails ::= SEQUENCE {
    /**
    * `TRUE` if this ticket is the participant card (= countermark) only, not valid without the real ticket of the ticket holder.
    * In case participant cards are used, all members of the group except the ticket holder (group leader) **SHALL** have this field set to `TRUE`.
    * Additionally, `linkedTickets` **SHOULD** be set to the ticket of the group leader.
    * `FALSE` if this ticket is the real ticket from the group leader.
    */
    isGroupParticipantCard  BOOLEAN,

    /**
    * Readable name of the group in case of a group ticket.
    */
    groupName               UnicodeText OPTIONAL
}

/**
* Types describing temporal conditions, used in several other type definitions
*/
ValidFrom ::= SEQUENCE {
    /**
    * Date/time validity in local time of the location where the journey starts.
    * Number of days from issuing date (-398 allows reissuing the ticket up to 13 months after the start of its validity, 800 allows issuing the ticket up to 2 years in advance).
    */
    validFromDay     INTEGER (-398..800)                DEFAULT 0,
    /**
    * A UTC offset **SHOULD NOT** be provided. In case a UTC offset is provided, the local date time is the time zone of the validity region, and the region where the ticket is valid **SHALL NOT** cover more than one time zone.
    * In case no UTC offset is provided, the local date time is the time zone of the current location of the traveler.
    */
    validFromTime    INTEGER (0..1439)                  DEFAULT 0
}

ValidUntil ::= SEQUENCE {
    /**
    * Date/time validity in local time of the location where the journey ends.
    * Number of days from validFrom date, 0 = validUntilDay is equal to the first day of validity.
    */
    validUntilDay     INTEGER (-1..500)            DEFAULT 0,
    validUntilTime    INTEGER (0..1439)            DEFAULT 1439
}

ExtendedValidUntil ::= SEQUENCE {
    /**
    * Extended date/time validity (up to just over 5 years) in local time of the location where the journey ends.
    * Number of days from validFrom date.
    */
    validUntilDay    INTEGER (501..2000),
    validUntilTime    INTEGER (0..1439)                 DEFAULT 1439
}

/**
* Time range when a product can be used.
* Use case examples:
* - School transport pass valid Monday through Friday, between 07:00 and 19:00, whether it is a pollution day or not, but not on public holidays:
*     `{ allowedWeekdays { monday TRUE, tuesday TRUE, wednesday TRUE, thursday TRUE, friday TRUE, saturday FALSE, sunday FALSE },
*        specialDays { nationalHolidays FALSE, stateHolidays FALSE, countyHolidays FALSE, localHolidays FALSE },
*        includedTimeRange { { fromTime 420, untilTime 1440 } } }`
* - Tourist week-end pass valid every Friday-Saturday-Sunday, whether it is a special day or not:
*     `{ allowedWeekdays { monday FALSE, tuesday FALSE, wednesday FALSE, thursday FALSE, friday TRUE, saturday TRUE, sunday TRUE } }`
* - Pollution ticket valid only on pollution days:
*     `{ specialDays { pollutionDay TRUE } }`
*/
IncludedTimeRanges ::= SEQUENCE {
    /**
    * Days of the week when the product can be used. For each day of the week:
    * - `TRUE` means the corresponding day is allowed.
    * - `FALSE` means the corresponding day is forbidden.
    *
    * However, this authorization **SHALL** take specialDays into account, if this element is also present.
    * If `allowedWeekDays` is omitted, the product validity does not depend on the day of the week.
    */
    allowedWeekdays              Weekdays                   OPTIONAL,

    /**
    * Impact of special days on product validity. This impact takes precedence over valid weekdays. For each special day:
    * - `TRUE` means the product can be used on this special day (even if the weekday is not allowed by allowedWeekdays).
    * - `FALSE` means the product can NOT be used on this special day (even if the weekday is allowed by allowedWeekdays).
    * - Omitted means that this special day does not affect the validity defined by allowedWeekdays.
    * If specialDays is omitted, the product validity does not depend on any special day.
    */
    specialDays                  SpecialDays                OPTIONAL,

    /**
    * Time ranges when the product can be used, during the days described above.
    * Omitted if the product validity does not depend on any time (but is defined for the entire days).
    */
    includedTimeRange            SEQUENCE OF TimeRange      OPTIONAL
}

Weekdays ::= SEQUENCE {
    monday              BOOLEAN,
    tuesday             BOOLEAN,
    wednesday           BOOLEAN,
    thursday            BOOLEAN,
    friday              BOOLEAN,
    saturday            BOOLEAN,
    sunday              BOOLEAN
}

/**
* The definition of what is a national, state, county, etc. holiday is per the tariff conditions of the product owner.
*/
SpecialDays ::= SEQUENCE {
    /**
    * National holiday (e.g. Christmas in France, as it is a public holiday throughout the whole country)
    */
    nationalHolidays    BOOLEAN OPTIONAL,
    /**
    * State holiday (e.g. Buss- und Bettag in the German Bundesland of Sachsen)
    */
    stateHolidays       BOOLEAN OPTIONAL,
    /**
    * County holiday (e.g. Corpus Christi).
    */
    countyHolidays      BOOLEAN OPTIONAL,
    /**
    * Local holiday (e.g. Friedensfest in the German city of Augsburg).
    */
    localHolidays       BOOLEAN OPTIONAL,
    /**
    * Days when pollution levels exceed the threshold.
    */
    pollutionDay        BOOLEAN OPTIONAL
}

/**
* Values referenced to local time
*/
TimeRange ::= SEQUENCE {
    fromTime                INTEGER (0..1439),
    untilTime               INTEGER (0..1439)
}

/**
* Product identification
*
* FIP products shall be coded under the product owner of ERA Org Code 3011 and product IDs of the
*  variant IA5 with said value starting with `FIP-`. The exact product IDs are left to be
*  defined by the FIP working group.
*/
Product ::= SEQUENCE {
    /**
    * Organization responsible for the product definition.
    * If omitted in `specificConditions`, `productOwner` is the one described in `generalConditions`.
    * If omitted in `generalConditions`, `productOwner` is the `issuer` element in `issuingDetail`.
    */
    productOwner        CompanyCode     OPTIONAL,

    /**
    * Product id to identify the issued product codelist defined by the product owner.
    */
    productId           GenericId   OPTIONAL,

    /**
    * Short readable description of the product.
    */
    productDescription  UnicodeText     OPTIONAL
}

/**
* Tariff data for transport products.
* Information included are:
*  - number, type and characteristics of allowed passengers, incl. applied reduction cards,
*  - optionally a link to the traveler data.
*/
Tariff ::= SEQUENCE {
    /**
    * Number of passengers using the tariff.
    */
    numberOfPassengers      INTEGER (1..200)        DEFAULT 1,

    /**
    * Type indication (youth, adult, senior... but also pet, bicycle).
    * The definition of which passenger is which type in this field is per the product owner.
    * Omitted if the ticket has no restrictions regarding the type of passenger,
    *  or if the restriction is based on the product type and not on this element.
    */
    passengerType           PassengerType           OPTIONAL,

    /**
    * Age restrictions of the tariff.
    */
    age CHOICE {
        specificAge INTEGER (0..127),
        ageRange    SEQUENCE {
            /**
            * 'below' is to be understood as 'strictly less than'
            */
            ageBelow    INTEGER (1..128) OPTIONAL,
            /**
            * 'above' is to be understood as 'strictly greater than'
            */
            ageAbove    INTEGER (0..127) OPTIONAL
        }
    } OPTIONAL,

    /**
    * Named traveler list.
    * Link to the traveler in case the travelers have to be named (e.g. Eurail passes).
    * The number indicates the position in the traveler sequence starting from 1.
    */
    travelerId              SEQUENCE (SIZE(1..254)) OF INTEGER (1..254) OPTIONAL,

    /**
    * Tariff code.
    */
    tariffId                GenericId               OPTIONAL,

    /**
    * Readable tariff description.
    */
    tariffDesc              UnicodeText             OPTIONAL,

    /**
    * Additional conditions applying specifically to this tariff entitlement.
    * These conditions restrict the circumstances in which the passengers
    * described by this `Tariff` are included in the transport product.
    *
    * They do not restrict the validity of the transport product for passengers
    * described by other `Tariff` elements.
    *
    * Index into `TransportProduct.conditions`.
    * The first element has index 1.
    */
    appliedConditionsIndex  INTEGER (1..32)         OPTIONAL
}

/**
* Card reference (for any kind of card: customer card, loyalty card, reduction card...)
*/
CardReference ::= SEQUENCE {
    /**
    * Issuer and type of the card.
    */
   	product Product,

    /**
    * According to `Format`, the ID is full, limited to the leading part, or limited to the trailing part.
    */
    id      GenericId       OPTIONAL,

    /**
    * Indication whether the full or only the leading or trailing part of the ID is provided.
    */
    format  IdFormat        DEFAULT full
}

/**
* Description of an identity document
* If number is not provided, this sequence merely defines the acceptable type of identification
* document, but does not specify an exact document; i.e. the traveler may be identified via
* their passport, but no stipulation is made on which specific passport is presented.
* If the country field is also blank, then this means any country (or no country at all) is valid.
*/
IdentificationDocument ::= SEQUENCE {
    /**
    * Numeric ISO 3166 country code of the issuing country of the document.
    */
    country     INTEGER (1..999)    OPTIONAL,

    /**
    * Category of the document (passport, ID card...).
    */
    category    IdentificationDocumentCategory,

    /**
    * Number of the document.
    */
    number      VisibleString       OPTIONAL,

    /**
    * Indication whether the full or only the leading or trailing part of the document number is provided.
    */
    format      IdFormat        DEFAULT trailingPart
}

/**
* Traveler data might contain all traveler details which are independent
*  from the type of travel document.
* E.g. it can include the date of birth as this is part of the traveler,
*  but not the indication "Senior" as this is tariff dependent.
*/
Traveler ::= SEQUENCE {
    name            Name,

    /**
    * The definition of which passenger is which type in this field is per the issuer,
    *  and may be overridden by product owner for a specific segment using `Tariff.passengerType`.
    */
    passengerType   PassengerType                               OPTIONAL,

    ageOrBirth CHOICE {
        dateOfBirth DateType,
        age         INTEGER (0..127)
    }                                                           OPTIONAL,

    rareDetails RareTravelerDetails                             OPTIONAL
}

/**
* Date type, used to indicate the date of birth.
* All elements are optional to allow indicating only a part of the date (e.g. only the year).
*/
DateType ::= SEQUENCE {
    year                     INTEGER    (1901..2155)                      OPTIONAL,
    month                    INTEGER    (1..12)                           OPTIONAL,
    day                      INTEGER    (1..31)                           OPTIONAL
}

/**
* Rare traveler data.
*/
RareTravelerDetails ::= SEQUENCE {
    /**
    * Details of the document (ID card, passport...) identifying the traveler.
    */
    identificationDocument           SEQUENCE (SIZE(1..16)) OF IdentificationDocument   OPTIONAL,

    /**
    * Cards (reduction, discount, loyalty...) held by the traveler.
    * Only present if they serve a purpose (e.g. access to a lounge in a station).
    */
    reductionCard                    SEQUENCE (SIZE(1..16)) OF CardReference            OPTIONAL,

    /**
    * Customer id might be numerical or alphanumerical.
    */
    customerId                       GenericId                                          OPTIONAL,

    /**
    * Omitted if no information is available.
    */
    passengerWithReducedMobility    BOOLEAN                                             OPTIONAL,

    /**
    * Country of residence (numeric ISO 3166 country code).
    * To be used in case there are product restrictions linked to the country of residence (e.g. Eurail passes),
    *   such restrictions are then indicated with the `countryValidity` element in `Tariff`.
    */
    countryOfResidence              INTEGER (1..999)                                    OPTIONAL,

    status                          SEQUENCE OF CustomerStatus                          OPTIONAL,

    /**
    * Proprietary data defined bilaterally.
    */
    extensions      SEQUENCE (SIZE(1..8)) OF Data{{TravelerExtensions}} (WITH COMPONENTS {
        ...,
        format (ALL EXCEPT "!C")
    }) OPTIONAL
}

TravelerExtensions DATA-ELEMENT ::= { ... }

/**
* Customer status
*/
CustomerStatus ::= SEQUENCE {
    /**
    * Company providing the status.
    * Omitted if this company is the ticket issuer.
    */
    statusProvider                 CompanyCode      OPTIONAL,
    customerStatus                 GenericId        OPTIONAL,
    /**
    * Customer status text description (e.g. "gold").
    */
    customerStatusDescr            VisibleString    OPTIONAL
}

/**
* Data for vouchers. Data included are quite basic, further study is required (e.g. through a meeting with people knowing vouchers).
*/
Voucher ::= SEQUENCE {
    controlData     ControlData,

    /**
    * Identification of the product (owner, id, textual description).
    */
    product         Product,

    /**
    * Begin / end of validity in local date wherever the traveler is located.
    * Valid from 00:00 to 23:59.
    * Number of year.
    */
    validFromYear   INTEGER (2016..2269),
    /**
    * Number of the day in the year (1.1. = 1).
    */
    validFromDay    INTEGER (0..500),

    /**
    * Number of year.
    */
    validUntilYear  INTEGER (2016..2269),
    /**
    * Number of the day in the year (1.1. = 1).
    */
    validUntilDay   INTEGER (0..500),

    /**
    * Value of the voucher, in the currency and fraction defined in IssuingData.
    */
    value           INTEGER                 DEFAULT 0,

    /**
    * Additional readable information that cannot be described using the other elements.
    */
    infoText        UnicodeText             OPTIONAL,

    /**
    * Proprietary data defined bilaterally.
    */
    extensions      SEQUENCE (SIZE(1..8)) OF Data{{VoucherExtensions}} (WITH COMPONENTS {
        ...,
        format (ALL EXCEPT "!P")
    }) OPTIONAL
}

VoucherExtensions DATA-ELEMENT ::= { ... }

VoucherConstraints ::= SEQUENCE {
    /**
    * Permitted currencies. If absent, any currency is permitted.
    */
    currency            SEQUENCE (SIZE(1..16)) OF SEQUENCE {
        currency        INTEGER (0..999) DEFAULT 978,
        maximumValue    SEQUENCE {
            value           INTEGER (0..MAX),
            currencyFract   INTEGER (0..3) DEFAULT 2
        } OPTIONAL
    } OPTIONAL,
    extensions  DataAuthorization{{VoucherExtensions}} OPTIONAL
}


/**
* Data for simple customer cards.
* For detailed or complex cards (e.g. valid only on a specific OD), use transportProduct instead.
* Included are data from:
*  - OEBB requirements on card data
*  - DB Bahncard as HandyTicket
*
* Note: customer data are included in the traveler data structure.
*/
CustomerCard ::= SEQUENCE {
    controlData         ControlData,

    /**
    * Identification of what variety of customer card it is.
    */
   	product             Product,
    /**
    * The ID identifying this specific card. The ID identifying the card product/variety goes into `product`.
    */
    individualCardId    GenericId,

    /**
    * Begin / end of validity in local date wherever the traveler is located.
    */
    validFrom           ValidFrom                                               OPTIONAL,
    validUntil          ValidUntil                                              OPTIONAL,

    /**
    * Travel class in case card usage is limited to a travel class.
    * For transport modes where the concept of class does not exist, this field **SHALL** be set to `notApplicable`.
    */
    classCode           TravelClass                                             OPTIONAL,

    /**
    * Proprietary data defined bilaterally.
    */
    extensions          SEQUENCE (SIZE(1..8)) OF Data{{CustomerCardExtensions}}   OPTIONAL
}

CustomerCardExtensions DATA-ELEMENT ::= { ... }

CustomerCardConstraints ::= SEQUENCE {
    extensions  DataAuthorization{{CustomerCardExtensions}} OPTIONAL
}

/**
* Data for parking as a standalone document.
* Included are data from:
* - DB parking ground reservation
*/
ParkingGround ::= SEQUENCE {
    controlData                 ControlData,

    /**
    * Identification of the product (owner, id, textual description).
    */
    product                     Product,

    /**
    * Start and end of validity of parking entitlement. Date and time in time zone of the parking.
    * When validFromTime == 0, validity is the whole day depending on opening hours of the parking facility.
    */
    validFrom                   ValidFrom,
    validUntil                  ValidUntil,

    parkingDetails              Parking
}

/**
* Data for parking as a leg of a global transport document.
* Suitable for cars but also for motorbikes, bikes. etc.
*/
Parking ::= SEQUENCE {
    /**
    * Code list of the product owner.
    */
    parkingGroundId VisibleString,

    /**
    * Code needed to access the parking lot.
    */
    accessCode      VisibleString                                           OPTIONAL,

    /**
    * Readable name of the parking location.
    * Omitted if the vehicle can park anywhere in the parking ground.
    */
    location        UnicodeText                                             OPTIONAL,

    /**
    * In case the parking ground is associated with a station.
    */
    station         Station                                                 OPTIONAL,

    /**
    * In case a special entry can or must be taken (e.g. VIP entry), readable name of this entry.
    */
    entryTrack      UnicodeText                                             OPTIONAL,

    /**
    * Number plate of the car parked.
    * See note in `CarCarriageReservationData` on the meaning of this field.
    */
    vehiclePlate    UnicodeText                                             OPTIONAL,

    /**
    * Number of days or hours of allowed parking in case this number is limited and less than the validity period.
    * If present, the count of the remaining number of allowed days or hours is centrally held in a back office,
    *   that must be queried to verify whether the traveler still has a right of parking.
    */
    numberAllowed CHOICE {
        days    INTEGER,
        minutes INTEGER (1..1439)
    }                                                                       OPTIONAL,

    /**
    * Additional readable information that cannot be described using the other elements.
    */
    infoText        UnicodeText                                             OPTIONAL,

    /**
    * Proprietary data defined bilaterally.
    */
    extensions          SEQUENCE (SIZE(1..8)) OF Data{{ParkingExtensions}}    OPTIONAL
}

ParkingExtensions DATA-ELEMENT ::= { ... }

ParkingConstraints ::= SEQUENCE {
    extensions  DataAuthorization{{ParkingExtensions}} OPTIONAL
}

/**
* Data for station passage and access.
* Ticket used to enter, exit or pass a station without traveling.
* e.g. for staff working in a station.
*/
StationPassage ::= SEQUENCE {
    controlData         ControlData,

    /**
    * Identification of the product (owner, id, textual description).
    */
    product             Product,

    /**
    * Station(s) concerned.
    */
    station             StationSet                                          OPTIONAL,

    /**
    * List of areas in a station where the access is allowed.
    * The code table used to identify the areas depends on the station.
    */
    area                SEQUENCE OF GenericId                               OPTIONAL,

    /**
    * Readable area names.
    * This field, if present, **SHALL** be of equal length to the `area` field.
    */
    areaNameUTF8        SEQUENCE OF UnicodeText                             OPTIONAL,

    /**
    * Period of validity of the right of passage.
    */
    validFrom           ValidFrom                                           OPTIONAL,
    validUntil          ValidUntil                                          OPTIONAL,

    /**
    * Number of days for station passage in case the number of days
    *  is limited and less than the validity period.
    * If present, the count of the remaining number of valid days is centrally held in a back office,
    *  that must be queried to verify whether the traveler still has a right of passage.
    */
    numberOfDaysValid   INTEGER                                             OPTIONAL,

    /**
    * Proprietary data defined bilaterally.
    */
    extensions          SEQUENCE (SIZE(1..8)) OF Data{{StationPassageExtensions}} OPTIONAL
}

StationPassageExtensions DATA-ELEMENT ::= { ... }

StationPassageConstraints ::= SEQUENCE {
    extensions  DataAuthorization{{StationPassageExtensions}} OPTIONAL
}

/**
* Example use cases:
*  - Identifier of the media linked with the barcode, e.g. the serial number of a Security In Paper ticket hosting the barcode
*  - Identifier of an ABT (Account Based Ticketing) system
*/
Token ::= SEQUENCE {
    /**
    * Provider of the token. Omitted if the provider is the `issuer` identified in IssuingData.
    */
    provider    CompanyCode         OPTIONAL,
    token       Data{{TokenTypes}}
}

sipSerialNumberToken DATA-ELEMENT ::= { VisibleString IDENTIFIED BY "SER" ENCODED WITH cuperEncoding CONSTRAINED BY NULL }
abtToken DATA-ELEMENT ::= { OCTET STRING IDENTIFIED BY "ABT" ENCODED WITH rawEncoding CONSTRAINED BY NULL }

TokenTypes DATA-ELEMENT ::= {
    sipSerialNumberToken |
    abtToken,
    ...
}

TokenConstraints ::= SEQUENCE {
    permittedProviders  CompanyConstraint,
    permittedTokenTypes DataAuthorization{{TokenTypes}} OPTIONAL
}

/**
* Confirmation of the delay of a transport
*/
DelayConfirmation ::= SEQUENCE {
    controlData     ControlData,

    /**
    * Transport number of the delayed transport.
    */
    transportNumber TransportId,
    /**
    * Line which the transport was operating as (e.g. S5)
    */
    lineNumber      LineId OPTIONAL,

    /**
    * Station where the delay became relevant, i.e. where passenger gets off the delayed transport, or the station
    * where they missed boarding when a transport left earlier than scheduled.
    */
    station         Station,
    /**
    * Planned arrival date and time at the station where delay became relevant.
    * Date referenced from issuing date.
    */
    arrival         ArrivalDateTime,

    /**
    * Indication if the transport has been delayed (and how long) or canceled.
    */
    delayType CHOICE {
        /**
        * The transport was delayed, and delay in minutes at the mentioned station.
        * The delay is negative if the transport left earlier than scheduled.
        */
        delay               INTEGER (-1439..1439),

        /**
        * The transport was cancelled.
        */
        transportCancelled  NULL,

        /**
        * The transport was cancelled, and replaced with a different transport.
        */
        replacedWith        SEQUENCE {
            /**
            * Transport number of the replacement transport.
            */
            transportNumber     TransportId,
            /**
            * Line which the replacement transport is operating as (e.g. S5 EV)
            */
            lineNumber          LineId          OPTIONAL,
            /**
            * The replacement transport is not calling at the original station, but is calling at a replacement station.
            */
            replacementStation  Station         OPTIONAL,
            /**
            * Planned arrival date and time at the original (or replacement) station of the replacement transport.
            * Date referenced from issuing date.
            */
            arrival             ArrivalDateTime
        },

        /**
        * The transport skipped a station, and optionally called at a replacement station
        */
        stationSkipped         SEQUENCE {
            replacement SEQUENCE {
                /**
                * The alternative station called at.
                */
                station  Station,
                /**
                * Planned arrival date and time at the replacement station of the replacement transport.
                * Date referenced from issuing date.
                */
                arrival             ArrivalDateTime
            } OPTIONAL
        }
    },

    /**
    * Type of confirmation provided.
    */
    confirmationType    DelayConfirmationType       DEFAULT travelerDelayConfirmation,

    /**
    * Affected original ticket(s).
    */
    affectedTickets     SEQUENCE OF TicketLink      OPTIONAL,

    /**
    * The validity of the original ticket is extended in some way.
    * If this field is unset, no statement is made about possibly validity extensions.
    * If it is set, but has no fields set within it, then the validity is explicitly not extended.
    */
    validityExtension   SEQUENCE {
        /**
        * Transport links have been waived.
        */
        transportLinkRemoved    BOOLEAN,
        /**
        * Additional transport links have been permitted.
        */
        additionalTransportLink SEQUENCE OF TransportLink,
        /**
        * Additional carriers the passenger is permitted to travel with.
        */
        additionalCarrier       SEQUENCE OF CompanyCode,
        /**
        * Additional service brands the passenger is permitted to travel in.
        * Per code list B.4.7009 of [](cite:tel-tsi-codes).
        */
        additionalServiceBrand  SEQUENCE OF INTEGER (1..32000)
    } OPTIONAL,

    /**
    * Additional readable information that cannot be described using the other elements.
    */
    infoText            UnicodeText                 OPTIONAL,

    /**
    * Proprietary data defined bilaterally.
    */
    extensions            SEQUENCE (SIZE(1..8)) OF Data{{DelayConfirmationExtensions}} (WITH COMPONENTS {
        ...,
        format (ALL EXCEPT ("!P"))
    }) OPTIONAL
}

DelayConfirmationExtensions DATA-ELEMENT ::= { ... }

DelayConfirmationConstraints ::= SEQUENCE {
    transportLinkRemoved    BOOLEAN DEFAULT FALSE,
    additionalTransportLink BOOLEAN DEFAULT FALSE,
    additionalCarrier       BOOLEAN DEFAULT FALSE,
    additionalServiceBrand  BOOLEAN DEFAULT FALSE,
    /**
    * If the relevant constraint is not present, the certificate is not permitted to issue such a delay confirmation.
    */
    extensions        DataAuthorization{{DelayConfirmationExtensions}} OPTIONAL
}

/**
* TicketLinkType is used to define a link from the ticket in the barcode to another ticket (requirement from Eurail).
* Known use cases:
*  - reservation of trailer and car carriage and traveler reservation.
*  - link between open ticket and bicycle reservations or pass.
*  - open ticket and vouchers for meals.
*/
TicketLink ::= SEQUENCE {
    /**
    * Data to reference the external ticket.
    */
    ticketIssuer        CompanyCode         OPTIONAL,
    ticketId            GenericId           OPTIONAL,

    /**
    * The product, or type of product, of that a linked ticket must have.
    * Useful in cases the exact linked ticket is not known, e.g. a 1st class upgrade to any second class ticket.
    */
    product             Product             OPTIONAL,

    /**
    * Readable name of the issuer of the external ticket.
    */
    ticketIssuerName    UnicodeText         OPTIONAL,

    /**
    * Type of linked ticket.
    */
    ticketType          ProductVariety      DEFAULT ticket:{},

    /**
    * Type of link.
    */
    linkMode            TicketLinkMode      DEFAULT issuedTogether
}

/**
* Sleeper compartment according to [](cite:tel-tsi-b5).
*/
BerthDetailData ::= SEQUENCE {
    berthType              BerthType,
    numberOfBerths         INTEGER (1..999),
    /**
    * Take particular care when using this field, in light of the CJEU decision C‑394/23.
    * Specifically: "the processing of personal data relating to the title of the customers
    *  of a transport undertaking, the purpose of which is to personalise the commercial communication
    *  based on their gender identity ... cannot be regarded as necessary for the performance of that contract"
    */
    gender                 CompartmentGender    DEFAULT mixed
}

/**
* The basis for these data is weak:
* - SCIC mentions a maximum of three pieces of hand luggage but does not include a definition of hand luggage.
* - SCIC refers to special conditions on registered luggage, but SCIC NRT does not contain definitions on that,
*     and UIC 108.1 does not contain data structures for luggage.
* - current THALYS luggage restrictions.
*/
LuggageRestriction ::= SEQUENCE {
    /**
    * Allowed hand luggage pieces on this ticket (3 = default in current NRT tariff).
    */
    maxHandLuggagePieces         INTEGER(0..99)                 DEFAULT 3,

    /**
    * Allowed non-hand luggage pieces on this ticket.
    */
    maxNonHandLuggagePieces      INTEGER(0..99)                 DEFAULT 1,

    registeredLuggage            SEQUENCE OF RegisteredLuggage  OPTIONAL
}

RegisteredLuggage ::= SEQUENCE {
    /**
    * ID of the additional registered luggage.
    * This field **MAY** refer to a [luggage tag](#luggage) issued for the luggage by being equal to its `id`, as 
    * specified in [](#luggage-ticket-link).
    */
    registrationId             GenericId        OPTIONAL,

    /**
    * Maximum weight in kg.
    */
    maxWeight                  INTEGER (1..99)  OPTIONAL,

    /**
    * Sum of length with and height in cm.
    */
    maxSize                   INTEGER (1..300)  OPTIONAL
}

/**
* Product variety indicates the type of the transport product, as well as some specific characteristics it may have.
*/
ProductVariety ::= CHOICE {
    /**
    * Ticket authorizing the use of the transportation service (single ticket, return ticket, ticket book, pass, access to a parking lot, car sharing service...)
    * This choice also describes some associated characteristics:
    * - how many journeys are possible (single/return/multiple/unlimited),
    * - is an online connection required to validate or check the ticket,
    * - is the ticket an initial ticket or an upgrade,
    * - does the ticket need an associated reservation to be usable.
    */
    ticket         TicketDetails,

    /**
    * Standalone reservation, which does not authorize travel unless accompanied by a ticket.
    */
    reservation    NULL,

    /**
    * Any card (reduction card, loyalty card...) that does not authorize travel but allows the holder to benefit from reduced prices or commercial advantages.
    */
    commercialCard NULL,

    /**
    * Very specific product, in case none of the above choices apply.
    */
    proprietary    NULL
}

TicketDetails ::= SEQUENCE {
    /**
    * Ticket category, indicating how many time the product can be used.
    */
    ticketCategory                TicketCategory     DEFAULT single,

    /**
    * Indicates if the ticket is an upgrade of another ticket.
    */
    isAnUpgrade                   BOOLEAN            DEFAULT FALSE,

    /**
    * Indicates if an associated reservation (as a separate standalone document) is required for the ticket to be usable:
    * - `TRUE` if an associated reservation is required.
    * - `FALSE` if no associated reservation is required (this value covers the case when the reservation is included in the ticket conditions).
    */
    additionalReservationRequired BOOLEAN            DEFAULT FALSE
}

TicketCategory ::= ENUMERATED {
    /**
    * Single ticket: only one journey is permitted.
    */
    single    (0),
    /**
    * Return ticket: only one outward journey and one return journey are permitted.
    */
    return    (1),
    /**
    * Multiple but not unlimited journeys are permitted (e.g. ticket book). The counting is made in a backoffice.
    */
    multiple  (2),
    /**
    * As many journeys as desired are permitted (e.g. pass).
    */
    unlimited (3)
}

ServiceType ::= ENUMERATED {
    seat              (0),
    couchette         (1),
    berth             (2),
    carCarriage       (3)
}

PassengerType ::= ENUMERATED {
    person          (0),
    senior          (1),
    child           (2),
    youth           (3),
    student         (4),
    youngChild      (5),
    /**
    * Child associated with a family traveling together.
    */
    familyChild     (6),
    /**
    * Accompanying person for PRM (Passenger with Restricted Mobility).
    */
    accompPRM       (7),
    /**
    * Passenger with wheel-chair.
    */
    wheelchair      (8),
    military        (9),
    /**
    * A pet but not a dog.
    */
    pet             (10),
    dog             (11),
    /**
    * An accompanying dog for a PRM (Passenger with Restricted Mobility).
    */
    accompDog       (12),
    bicycle         (13),
    /**
    * Can be used for e.g. unaccompanied luggage.
    */
    luggage         (14)
}

TicketLinkMode ::= ENUMERATED {
    issuedTogether         (0),
    onlyValidInCombination (1)
}

DelayConfirmationType ::= ENUMERATED {
    /**
    * Confirmation of transport delay, whether the traveler was on board in unconfirmed.
    */
    transportDelayConfirmation    (0),
    /**
    * Confirmation that the traveler was on board of the delayed transport.
    */
    travelerDelayConfirmation     (1),
    /**
    * Confirmation that a ticket linked to the delayed transport was issued.
    */
    transportLinkedTicketDelay    (2)
}

BerthType ::= ENUMERATED {
    single     (0),
    special    (1),
    double     (2),
    t2         (3),
    t3         (4),
    t4         (5)
}

CompartmentGender ::= ENUMERATED {
    unspecified    (0),
    family         (1),
    female         (2),
    male           (3),
    mixed          (4)
}

IdFormat ::= ENUMERATED {
    full              (0),
    leadingPart       (1),
    trailingPart      (2)
}

IdentificationDocumentCategory ::= ENUMERATED {
    passport              (0),
    idCard                (1),
    residencePermit       (2),
    driverLicense         (3),
    creditCard            (4),
    socialBenefitsCard    (5),
    studentIdCard         (6),
    /**
    * e.g. those issued under the Convention of the 28th of September 1954, or a Laissez-Passer
    */
    specialTravelDocument (7)
}

TravelClass ::= ENUMERATED {
    notApplicable  (0),
    first          (1),
    second         (2),
    tourist        (3),
    comfort        (4),
    premium        (5),
    business       (6),
    all            (7),
    premiumFirst   (8),
    standardFirst  (9),
    premiumSecond  (10),
    standardSecond (11)
}

CountryValidity ::= ENUMERATED {
   onlyInCountryOfResidence    (0),
   includingCountryOfResidence (1),
   excludingCountryOfResidence (2)
}

LoadingDeck ::= ENUMERATED {
    upper                (0),
    lower                (1)
}

CompartmentPosition ::= ENUMERATED {
    upperLevel           (0),
    lowerLevel           (1)
}

RoofRack ::= ENUMERATED {
    norack               (0),
    roofRailing          (1),
    luggageRack          (2),
    skiRack              (3),
    boxRack              (4),
    rackWithOneBox       (5),
    rackWithTwoBoxes     (6),
    bicycleRack          (7),
    otherRack            (8)
}

RetailChannel ::= ENUMERATED {
    /**
    * SMS sent to a specific number.
    */
    smsTicket            (0),
    /**
    * Application on a mobile phone.
    */
    mobileApplication    (1),
    /**
    * Internet portal.
    */
    webSite              (2),
    /**
    * Agency or counter.
    */
    ticketOffice         (3),
    /**
    * Dealer (e.g. tobacconist, newsagent, cafe, etc.).
    */
    depositaryTerminal   (4),
    /**
    * On-board sales (e.g. using the driver's point-of-sale terminal).
    */
    onBoardTerminal      (5),
    /**
    * Automatic sales machine.
    */
    ticketVendingMachine (6)
}

END
