/**
* BT4PT Envelope - DRAFT.
*
* The envelope **SHALL** be encoded with the Aligned Packed Encoding Rules, as this makes it easier to work with in constrained environments such as HSMs.
* Data elements within the header **SHOULD** be encoded with the Unaligned Packed Encoding Rules, for space savings.
*/
BT4PT-EnvelopeV1-0 {
    iso(1) identified-organization(3) dod(6) internet(1) private(4) enterprise(1) uic(17218) fcb(1) bt4pt(2) envelope(2) v1(1) 0
} DEFINITIONS ::= BEGIN

EXPORTS BT4PTEnvelope, SecurityProviderDataElements;
IMPORTS CompanyCode, Timestamp, TimestampSeconds, Data, DSSSignature, ECPublicKey, DATA-ELEMENT
 FROM BT4PT-GeneralElementsV1-0 { iso(1) identified-organization(3) dod(6) internet(1) private(4) enterprise(1) uic(17218) fcb(1) bt4pt(2) general(1) v1(1) 0 }
 EndEntityCertificate
 FROM BT4PT-CertificatesV1-0 { iso(1) identified-organization(3) dod(6) internet(1) private(4) enterprise(1) uic(17218) fcb(1) bt4pt(2) certificates(7) v1(1) 0 }
 multiModalTicketData
 FROM BT4PT-MultiModalTicketDataV1-0 { iso(1) identified-organization(3) dod(6) internet(1) private(4) enterprise(1) uic(17218) fcb(1) bt4pt(2) mmtd(3) v1(1) 0 }
 dynamicContentData, dynamicContentDataAligned
 FROM BT4PT-DynamicContentDataV1-0 { iso(1) identified-organization(3) dod(6) internet(1) private(4) enterprise(1) uic(17218) fcb(1) bt4pt(2) dcd(4) v1(1) 0 }
 fixedPointData
 FROM BT4PT-FixedPointDataV1-0 { iso(1) identified-organization(3) dod(6) internet(1) private(4) enterprise(1) uic(17218) fcb(1) bt4pt(2) fpd(5) v1(1) 0 }
 encryptedData
 FROM BT4PT-EncryptedDataV1-0 { iso(1) identified-organization(3) dod(6) internet(1) private(4) enterprise(1) uic(17218) fcb(1) bt4pt(2) encryptedData(11) v1(1) 0 }
 luggageTag
 FROM BT4PT-LuggageTagV1-0 { iso(1) identified-organization(3) dod(6) internet(1) private(4) enterprise(1) uic(17218) fcb(1) bt4pt(2) luggageTag(12) v1(1) 0 }
 hsmTraceData
 FROM BT4PT-HSMTraceV1-0 { iso(1) identified-organization(3) dod(6) internet(1) private(4) enterprise(1) uic(17218) fcb(1) bt4pt(2) hsm(6) v1(1) 0 }
 uicRailTicketData
 FROM RailTicketDataV3 { iso(1) identified-organization(3) dod(6) internet(1) private(4) enterprise(1) uic(17218) fcb(1) modules(0) rtd(2) v3(3) 7 }
 uicRailTicketData
 FROM RailTicketDataV2 { iso(1) identified-organization(3) dod(6) internet(1) private(4) enterprise(1) uic(17218) fcb(1) modules(0) rtd(2) v2(2) 3 }
 uicRailTicketData
 FROM RailTicketDataV1 { iso(1) identified-organization(3) dod(6) internet(1) private(4) enterprise(1) uic(17218) fcb(1) modules(0) rtd(2) v1-3(1) 5 }
 uicDynamicContentData
 FROM DynamicContentDataV1 { iso(1) identified-organization(3) dod(6) internet(1) private(4) enterprise(1) uic(17218) fcb(1) modules(0) dcd(3) v1(1) 5 };

/**
* This data structure is the basic entry point of the envelope.
* A BT4PT envelope **SHALL** consist of the bytes resulting from encoding this data structure using the Canonical Aligned Packed Encoding Rules, per [](cite:x691).
*/
BT4PTEnvelope ::= CHOICE {
    /**
    * This variant contains the list of data elements that the envelope encodes, in an unsigned fashion, with no
    * additional security data.
    *
    * This variant **SHALL** only be used where no security is required. That is, when an unsigned envelope
    * is considered suitable for the application.
    */
    unsigned    [1] SEQUENCE (SIZE(1..16)) OF Data{{SecurityProviderDataElements}} (WITH COMPONENTS {
        ...,
        format (ALL EXCEPT ("!I" | "!C" | "!P"))
    }),
    /**
    * This variant is used for a signed envelope. It contains the list of data elements that the envelope encodes,
    * along with a signature from the Security Provider, the certificate for the end-entity that output this envelope,
    * and an optional binding of this envelope to a end-device's public key.
    */
    signed      [2] SEQUENCE {
        /**
        * This field contains the Security Provider Signed Data, as well as any additional data to be signed by the device.
        */
        data            DeviceSignedData,
        /**
        * This field is used as part of the device binding of envelopes. When an envelope is bound to a Presentment
        * Device, it **SHALL** contain a signature, calculated over the Canonical Aligned Packed Encoding Rules encoding
        * of {@link DeviceSignedData}, using the device held private key corresponding to the public key provided in the
        * `deviceBinding.level2PublicKey` field of {@link SecurityProviderSignedData}.
        *
        * If the `deviceBinding` field of the {@link SecurityProviderSignedData} is unset, and this field is set, the envelope **SHALL** be
        * construed as invalid.
        * If the `deviceBinding` field of the {@link SecurityProviderSignedData} is set, and this field is unset, the envelope **SHALL** be
        * construed as invalid.
        */
        deviceSignature Signature OPTIONAL
    }
}

DeviceSignedData ::= SEQUENCE {
    /**
    * This field contains the data signed by the Security Provider, in a message recovery fashion.
    * Its inner data is the Canonical Aligned Packed Encoding Rules encoding of {@link SecurityProviderSignedData}, prefixed with
    * the first 16 bytes of the SHA-256 hash of the encoding.
    */
    data        MessageRecoverySignature,
    /**
    * This field contains the end-entity certificate used to sign the `data` field.
    */
    certificate EndEntityCertificate,
    /**
    * This field contains the timestamp at which the Presentment Device generated the envelope.
    *
    * This field **SHALL** be set if the `deviceBinding` field of the {@link SecurityProviderSignedData} is set, otherwise the
    * envelope **SHALL** be construed as invalid.
    * If this timestamp is more than the `deviceBinding.validityDuration` field of the {@link SecurityProviderSignedData} seconds
    * in the past, the envelope **SHALL** be construed as invalid, subject to the clock tolerance specified in
    * [](#clock-skew).
    *
    * A Presentment Device **SHALL NOT** rely on its local clock alone when generating the `timestamp` of the device
    * signed data. It **SHALL** determine the offset of its local clock from the time of a reliable source, such as the
    * systems of the issuer, whenever it is online, and **SHALL** correct the `timestamp` by that offset. A Presentment
    * Device whose clock is set incorrectly, whether accidentally or deliberately, will otherwise generate envelopes
    * that are rejected as expired or as having a timestamp in the future.
    */
    timestamp   TimestampSeconds   OPTIONAL,
    /**
    * This field contains data elements signed only by the Presentment Device, or not signed at all.
    * Note: the inclusion of device data without the `SecurityProviderSignedData.deviceBinding` field being set is _not_ an error.
    * It is permissible to include unauthenticated device data, for example as a debugging aid.
    */
    deviceData  SEQUENCE (SIZE(1..8)) OF Data{{DeviceDataElements}} (WITH COMPONENTS {
        ...,
        format (ALL EXCEPT ("!I" | "!C" | "!P"))
    }) OPTIONAL
}

SecurityProviderSignedData ::= [APPLICATION 12] SEQUENCE {
    /**
    * This field contains data elements signed by the Security Provider.
    */
    data                SEQUENCE (SIZE(1..64)) OF Data{{SecurityProviderDataElements}} (WITH COMPONENTS {
        ...,
        format (ALL EXCEPT ("!I" | "!C" | "!P"))
    }),
    /**
    * This field allows for the encoding of an expiry date for the envelope. After this timestamp the envelope needs to
    * be regenerated by the Security Provider for it to remain valid.
    *
    * Note: this is different from the ticket validity encoded in a data element. An envelope could be valid for more or
    * for less time than the transport product encoded in a data element.
    */
    endOfValidity       Timestamp   OPTIONAL,
    /**
    * This field allows for the binding of a barcode envelope to a specific end-device.
    */
    deviceBinding       [1] SEQUENCE {
        /**
        * If device binding is in use, this field **SHALL** contain the public-key of the Presentment Device.
        */
        level2PublicKey     CHOICE {
            /**
            * A point on the [NIST P-256](cite:nist-sp800-186) curve.
            */
            nistP256    [1] ECPublicKey{32},
            /**
            * A point on the [NIST P-384](cite:nist-sp800-186) curve.
            */
            nistP384    [3] ECPublicKey{48},
            /**
            * A point on the [NIST P-521](cite:nist-sp800-186) curve.
            */
            nistP521    [4] ECPublicKey{66},
            /**
            * The compressed encoding of an Ed25519 point, per [](cite:rfc8032).
            */
            ed25519     [5] OCTET STRING (SIZE (32)),
            /**
            * The compressed encoding of an Ed448 point, per [](cite:rfc8032).
            */
            ed448       [6] OCTET STRING (SIZE (57)),
            /**
            * If the public-key is not one of the above types, this variant **SHALL** be used, and **SHALL** contain the
            * an [X.509](cite:x509) `SubjectPublicKeyInfo` structure, encoded according to the Distinguished Encoding
            * Rules per [](cite:x690).
            */
            other       [7] OCTET STRING
        },
        /**
        * This field sets how long, in seconds, an envelope signed by the Presentment Device stays valid after generation.
        * This value **SHOULD NOT** be less than 30 seconds, as a shorter duration leaves little margin for clock skew, etc.
        */
        validityDuration    INTEGER (1..3600)
   	} OPTIONAL
}

/**
* The following data elements can appear in the `data` field of the {@link SecurityProviderSignedData} structure.
* Note: other data elements, not defined in this standard, are also permitted to appear.
*/
SecurityProviderDataElements DATA-ELEMENT ::= {
    multiModalTicketData |
    fixedPointData |
    luggageTag |
    encryptedData |
    hsmTraceData |
    RailTicketDataV3.uicRailTicketData |
    RailTicketDataV2.uicRailTicketData |
    RailTicketDataV1.uicRailTicketData,
    ...
}

/**
* The following data elements can appear in the `deviceData` field of the {@link DeviceSignedData} structure.
* Note: other data elements, not defined in this standard, are also permitted to appear.
*
* The difference between `DCD1` and `DCD1A` is that the first uses unaligned packed encoding and the second uses
* aligned packed encoding; otherwise, they are identical.
*/
DeviceDataElements DATA-ELEMENT ::= {
    dynamicContentData |
    dynamicContentDataAligned |
    DynamicContentDataV1.uicDynamicContentData,
    ...
}

/**
* Message recovery signature as per [](cite:iso9796-3 "13").
* @len The length, in bytes, of each of `r` and `s`. That is, half the total signature length.
*/
ECKNRSignature{INTEGER: len} ::= SEQUENCE {
    /**
    * The output r of the ECKNR signature process.
    */
    r OCTET STRING (SIZE(len)),
    /**
    * The output s of the ECKNR signature process.
    */
    s OCTET STRING (SIZE(len)),
    /**
    * The non-recoverable data part. That is, the remaining data of the ECKNR signature process.
    */
    remainder OCTET STRING
}

/**
* This data structure contains a Elliptic Curve KCDSA/Nyberg-Rueppel message recovery signature.
* Such a signature is defined in [](cite:iso9796-3 "13")
*/
MessageRecoverySignature ::= [APPLICATION 11] CHOICE {
    /**
    * An ECKNR signature over the [NIST P-256](cite:nist-sp800-186) curve with the [SHA-256 hash function](cite:fips180).
    */
    es256   [1] ECKNRSignature{32},
    /**
    * An ECKNR signature over the [NIST P-384](cite:nist-sp800-186) curve with the [SHA-384 hash function](cite:fips180).
    */
    es384   [3] ECKNRSignature{48},
    /**
    * An ECKNR signature over the [NIST P-521](cite:nist-sp800-186) curve with the [SHA-512 hash function](cite:fips180).
    */
    es512   [4] ECKNRSignature{66}
}

/**
* This data structure contains a non-message recovery (i.e. standard) signature.
*/
Signature ::= CHOICE {
    /**
    * An [ECDSA](cite:x9.62) signature over the [NIST P-256](cite:nist-sp800-186) curve with the [SHA-256 hash function](cite:fips180).
    */
    es256       [1] DSSSignature{32},
    /**
    * An [ECDSA](cite:x9.62) signature over the [NIST P-384](cite:nist-sp800-186) curve with the [SHA-384 hash function](cite:fips180).
    */
    es384       [3] DSSSignature{48},
    /**
    * An [ECDSA](cite:x9.62) signature over the [NIST P-521](cite:nist-sp800-186) curve with the [SHA-512 hash function](cite:fips180).
    */
    es512       [4] DSSSignature{66},
    /**
    * An [EdDSA](cite:rfc8032) signature over Curve25519.
    */
    ed25519     [5] OCTET STRING (SIZE (64)),
    /**
    * An [EdDSA](cite:rfc8032) signature over Curve448.
    */
    ed448       [6] OCTET STRING (SIZE (114)),
    /**
    * If the signature scheme is not one of the above types, this variant **SHALL** be used.
    */
    other       [7] SEQUENCE {
        /**
        * An object identifier specifying which signature scheme is in use.
        */
        algId       OBJECT IDENTIFIER,
        /**
        * The encoded signature, as per the above `algId`.
        */
        signature   OCTET STRING
    }
}

END
