/**
* UIC barcode header - version 3.0.0
*
* ## Encoding conventions
* A barcode which is only static, and for which the security is in the system (e.g. security paper), does not need a signature.
* A barcode which is only static, and includes its own security, needs a level 1 signature and a corresponding key reference.
* A dynamic barcode including static and dynamic signatures needs the same elements as a static barcode, plus a level 2 signature.
*
* The maximum size of a barcode is, per the Aztec specification ISO 24778, limited to 1914 bytes.
*/
BarcodeHeader { iso(1) identified-organization(3) dod(6)
    internet(1) private(4) enterprise(1) uic(17218) fcb(1) modules(0) header(1) v3(3) 0 }
    DEFINITIONS AUTOMATIC TAGS ::= BEGIN

EXPORTS BarcodeHeader;
IMPORTS CompanyCode, Timestamp, DataFormatIdentifier, Data, DATA-ELEMENT
 FROM GeneralData { iso(1) identified-organization(3) dod(6) internet(1) private(4) enterprise(1) uic(17218) fcb(1) modules(0) general(5) v1(1) 0 }
 multiModalTicketData
 FROM MultiModalTicketData { iso(1) identified-organization(3) dod(6) internet(1) private(4) enterprise(1) uic(17218) fcb(1) modules(0) mmtd(4) v1(1) 0 }
 dynamicContentData
 FROM DynamicContentData { iso(1) identified-organization(3) dod(6) internet(1) private(4) enterprise(1) uic(17218) fcb(1) modules(0) dcd(3) v2(2) 0 }
 fixedPointData
 FROM FixedPointData { iso(1) identified-organization(3) dod(6) internet(1) private(4) enterprise(1) uic(17218) fcb(1) modules(0) fpd(6) v1(1) 0 }
 uicRailTicketData
 FROM RailTicketDataV3 { iso(1) identified-organization(3) dod(6) internet(1) private(4) enterprise(1) uic(17218) fcb(1) modules(0) rtd(2) v3(3) 7 }
 uicRailTicketData
 FROM RailTicketDataV2 { iso(1) identified-organization(3) dod(6) internet(1) private(4) enterprise(1) uic(17218) fcb(1) modules(0) rtd(2) v2(2) 3 }
 uicRailTicketData
 FROM RailTicketDataV1 { iso(1) identified-organization(3) dod(6) internet(1) private(4) enterprise(1) uic(17218) fcb(1) modules(0) rtd(2) v1-3(1) 5 }
 uicDynamicContentData
 FROM DynamicContentDataV1 { iso(1) identified-organization(3) dod(6) internet(1) private(4) enterprise(1) uic(17218) fcb(1) modules(0) dcd(3) v1(1) 5 };

/**
* The basic entry point of the barcode.
*/
BarcodeHeader ::= SEQUENCE {
    /**
    * This field **SHALL** be set to the byte string `U3`.
    * This results in the version 3 header being prefixed with U3 at the start, allowing identification of this
    *  format of barcode header.
    */
    format      OCTET STRING (SIZE(2)),
    contents    SEQUENCE {
        level2Data      Level2Data,
        /**
        * If the the `BarcodeData.level2PublicKey` field is unset, and this field is set, the barcode is invalid.
        * If the the `BarcodeData.level2PublicKey` field is set, and this field is unset, the barcode is invalid.
        * The signature is calculated over the CUPER encoding of `Level2Data`.
        */
        level2Signature Signature OPTIONAL
    }
}

Level2Data ::= SEQUENCE {
    level1Data  Level1Data,
    /**
    * Dynamic Content Data goes here.
    */
    data  SEQUENCE (SIZE(1..8)) OF Data{Level2DataElements} (WITH COMPONENTS {
        ...,
        format (ALL EXCEPT ("!I" | "!C" | "!P"))
    }) OPTIONAL
}

Level1Data ::= CHOICE {
    /**
    * Only permitted where no security is required.
    * In this case, `BarcodeData.level2PublicKey` **MUST** be unset.
    */
    unsigned                BarcodeData,
    standardSigned          SEQUENCE {
        keyReference    CompanyKeyReference,
        data            BarcodeData,
        /**
        * Signature calculated over the CUPER encoding of `BarcodeTBSData`.
        */
        signature       Signature
    },
    messageRecoverySigned   SEQUENCE {
        keyReference    CompanyKeyReference,
        /**
        * Signed content is `BarcodeData`.
        */
        data            MessageRecoverySignature
    },
    subIssued               SEQUENCE {
        certificate     EndEntityCertificate,
        /**
        * Signed content is `BarcodeData`.
        */
        data            MessageRecoverySignature
    }
}

BarcodeTBSData ::= SEQUENCE {
    keyReference    CompanyKeyReference,
    data            BarcodeData
}

/**
* Provider of the level 1 signature.
*/
CompanyKeyReference ::= SEQUENCE {
    securityProvider    CompanyCode,
    keyId               INTEGER (0..99999)
}

/**
* Values taken from the IANA [JSON Web Signature and Encryption Algorithm registry](https://www.iana.org/assignments/jose/jose.xhtml#web-signature-encryption-algorithms).
*/
Signature ::= CHOICE {
    /**
    * ECDSA using the NIST P-256 curve and SHA-256.
    */
    es256       DSSSignature{32},
    /**
    * ECDSA using the secp256k1 curve and SHA-256.
    */
    es256k      DSSSignature{32},
    /**
    * ECDSA using the NIST P-384 curve and SHA-384.
    */
    es384       DSSSignature{48},
    /**
    * ECDSA using the NIST P-521 curve and SHA-512.
    */
    es512       DSSSignature{66},
    ed25519     OCTET STRING (SIZE (64)),
    ed448       OCTET STRING (SIZE (114)),
    /**
    * HMAC using SHA-256, not permitted except by bilateral agreement.
    */
    hs256       OCTET STRING (SIZE (32)),
    /**
    * HMAC using SHA-384, not permitted except by bilateral agreement.
    */
    hs384       OCTET STRING (SIZE (48)),
    /**
    * HMAC using SHA-512, not permitted except by bilateral agreement.
    */
    hs512       OCTET STRING (SIZE (64)),
    /**
    * DSA-1024 using SHA-1, not recommended for new deployments.
    */
    dsa1        DSSSignature{20},
    /**
    * DSA-2048 using SHA-224, not recommended for new deployments.
    */
    dsa224      DSSSignature{32},
    /**
    * DSA-2048 using SHA-256, not recommended for new deployments.
    */
    dsa256      DSSSignature{32},
    /**
    * Space for future signature modes, e.g. Post-Quantum Cryptography.
    */
    reserved1   NULL,
    /**
    * Space for future signature modes, e.g. Post-Quantum Cryptography.
    */
    reserved2   NULL,
    /**
    * Space for future signature modes, e.g. Post-Quantum Cryptography.
    */
    reserved3   NULL,
    other       SEQUENCE {
        algId       OBJECT IDENTIFIER,
        signature   OCTET STRING
    }
}

/**
* A generic container for the conveyance of Digital Signature Scheme signatures, e.g. ECDSA and DSA.
* @len The length, in bytes, of each of `r` and `s`. That is, half the total signature length.
*/
DSSSignature{INTEGER: len} ::= SEQUENCE {
    r OCTET STRING (SIZE(len)),
    s OCTET STRING (SIZE(len))
}

MessageRecoverySignature ::= CHOICE {
    /**
    * NIST P-256 curve and SHA-256.
    */
    es256   ECKNRSignature{32},
    /**
    * secp256k1 curve and SHA-256.
    */
    es256k  ECKNRSignature{32},
    /**
    * NIST P-384 curve and SHA-384.
    */
    es384   ECKNRSignature{48},
    /**
    * NIST P-521 curve and SHA-512.
    */
    es512   ECKNRSignature{66}
}

/**
* Message recovery signature as per ISO/IEC 9796-3:2006 Sec. 13 (ECKNR).
* @len The length, in bytes, of each of `r` and `s`. That is, half the total signature length.
*/
ECKNRSignature{INTEGER: len} ::= SEQUENCE {
    r OCTET STRING (SIZE(len)),
    s OCTET STRING (SIZE(len)),
    remainder OCTET STRING
}

PublicKey ::= CHOICE {
    nistP256    ECPublicKey{32},
    secp256K1   ECPublicKey{32},
    nistP384    ECPublicKey{48},
    nistP521    ECPublicKey{66},
    ed25519     OCTET STRING (SIZE (32)),
    ed448       OCTET STRING (SIZE (57)),
    /**
    * Space for future public key formats, e.g. Post-Quantum Cryptography.
    */
    reserved    NULL,
    /**
    * DER encoded SubjectPublicKeyInfo.
    */
    other       OCTET STRING
}

/**
* @len The length, in bytes, required to represent the x coördinate on a curve.
*/
ECPublicKey{INTEGER: len} ::= SEQUENCE {
    x OCTET STRING (SIZE(len)),
    yIsOdd BOOLEAN
}

EndEntityCertificate ::= SEQUENCE {
    serial INTEGER (1..16777216),
    issuer CompanyKeyReference,
    validUntilYear INTEGER (2026..2279),
    validUntilDay INTEGER (1..366),
    /**
    * The public key **MUST** be of the same EC curve as the issuing certificate's public key.
    * If it is not the certificate **MUST** be treated as invalid.
    * This public key is calculated as per [SEC 4](https://www.secg.org/sec4-1.0.pdf).
    */
    subjectPublicKey CHOICE {
        nistP256    ECPublicKey{32},
        secp256K1   ECPublicKey{32},
        nistP384    ECPublicKey{48},
        nistP521    ECPublicKey{66}
    },
    extensions SEQUENCE OF CertificateExtension (SIZE(0..15))
}

CertificateExtension ::= SEQUENCE {
    extension   Data{CertificateExtensions} (WITH COMPONENTS {
        ...,
        format (ALL EXCEPT ("!I" | "!C" | "!P"))
    }),
    /**
    * If the extension format is not recognised, or can't be processed, and it is marked critical, the certificate **MUST** be treated as invalid;
    * otherwise, it is permitted to ignore extensions not understood.
    */
    critical    BOOLEAN
}

CertificateExtensions DATA-ELEMENT ::= { ... }

BarcodeData ::= SEQUENCE {
    /**
    * This field MUST contain at most one well-known UIC data type (e.g. `FCBn`).
    */
    data                SEQUENCE SIZE(1..16) OF Data{Level1DataElements} (WITH COMPONENTS {
        ...,
        format (ALL EXCEPT ("!I" | "!C" | "!P"))
    }),
    level2PublicKey     PublicKey                       OPTIONAL,
    /**
    * End of the validity of the barcode.
    * After this date and time the barcode needs to be regenerated by the provider of the ticket.
    * The provider of the bar code **MUST** ensure that the endOfValidity given here does not exceed the validity of the key pair used on level 2.
    */
    endOfValidity       Timestamp                       OPTIONAL,
    /**
    * Validity duration in seconds of the barcode with reference to the time stamp in the dynamic content data.
    */
   	validityDuration    INTEGER (1..3600)               OPTIONAL,
   	...
}

Level1DataElements DATA-ELEMENT ::= {
    multiModalTicketData |
    fixedPointData |
    RailTicketDataV3.uicRailTicketData |
    RailTicketDataV2.uicRailTicketData |
    RailTicketDataV1.uicRailTicketData,
    ...
}
Level2DataElements DATA-ELEMENT ::= {
 dynamicContentData |
 DynamicContentDataV1.uicDynamicContentData,
 ...
}

END
