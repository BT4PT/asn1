UIC-Object-Identifiers { iso(1) identified-organization(3) dod(6)
    internet(1) private(4) enterprise(1) uic(17218) fcb(1) modules(0) oids(0) }
    DEFINITIONS ::= BEGIN

EXPORTS ALL;

uicFcb OBJECT IDENTIFIER ::= { iso(1) identified-organization(3) dod(6)
    internet(1) private(4) enterprise(1) uic(17218) fcb(1) }

uicFcbAsn1Modules OBJECT IDENTIFIER ::= { uicFcb modules(0) }

uicPki OBJECT IDENTIFIER ::= { uicFcb pki(1) }

-- This module
objectIdentifiersModule OBJECT IDENTIFIER ::= { uicFcbAsn1Modules oids(0) }

-- UIC Barcode Header - version 1.0.0
uicBarcodeHeaderV1-0-0 OBJECT IDENTIFIER ::= { uicFcbAsn1Modules header(1) v1(1) 0 }

-- UIC Barcode Header - version 2.0.0
uicBarcodeHeaderV2-0-0 OBJECT IDENTIFIER ::= { uicFcbAsn1Modules header(1) v2(2) 0 }

-- UIC Barcode Header - version 2.0.1
uicBarcodeHeaderV2-0-1 OBJECT IDENTIFIER ::= { uicFcbAsn1Modules header(1) v2(2) 1 }

-- UIC Barcode Header - version 3.0.0, currently a draft
uicBarcodeHeaderV3-0-0 OBJECT IDENTIFIER ::= { uicFcbAsn1Modules header(1) v3(3) 0 }

-- UIC Rail Ticket Data - version 1.3.0
uicRailTicketDataV1-3-0 OBJECT IDENTIFIER ::= { uicFcbAsn1Modules rtd(2) v1-3(1) 0 }

-- UIC Rail Ticket Data - version 1.3.1
uicRailTicketDataV1-3-1 OBJECT IDENTIFIER ::= { uicFcbAsn1Modules rtd(2) v1-3(1) 1 }

-- UIC Rail Ticket Data - version 1.3.3
uicRailTicketDataV1-3-3 OBJECT IDENTIFIER ::= { uicFcbAsn1Modules rtd(2) v1-3(1) 3 }

-- UIC Rail Ticket Data - version 1.3.4
uicRailTicketDataV1-3-4 OBJECT IDENTIFIER ::= { uicFcbAsn1Modules rtd(2) v1-3(1) 4 }

-- UIC Rail Ticket Data - version 1.3.5
uicRailTicketDataV1-3-5 OBJECT IDENTIFIER ::= { uicFcbAsn1Modules rtd(2) v1-3(1) 5 }

-- UIC Rail Ticket Data - version 2.0.0
uicRailTicketDataV2-0-0 OBJECT IDENTIFIER ::= { uicFcbAsn1Modules rtd(2) v2(2) 0 }

-- UIC Rail Ticket Data - version 2.0.1
uicRailTicketDataV2-0-1 OBJECT IDENTIFIER ::= { uicFcbAsn1Modules rtd(2) v2(2) 1 }

-- UIC Rail Ticket Data - version 2.0.2
uicRailTicketDataV2-0-2 OBJECT IDENTIFIER ::= { uicFcbAsn1Modules rtd(2) v2(2) 2 }

-- UIC Rail Ticket Data - version 2.0.3
uicRailTicketDataV2-0-3 OBJECT IDENTIFIER ::= { uicFcbAsn1Modules rtd(2) v2(2) 3 }

-- UIC Rail Ticket Data - version 3.0.0
uicRailTicketDataV3-0-0 OBJECT IDENTIFIER ::= { uicFcbAsn1Modules rtd(2) v3(3) 0 }

-- UIC Rail Ticket Data - version 3.0.1
uicRailTicketDataV3-0-1 OBJECT IDENTIFIER ::= { uicFcbAsn1Modules rtd(2) v3(3) 1 }

-- UIC Rail Ticket Data - version 3.0.2
uicRailTicketDataV3-0-2 OBJECT IDENTIFIER ::= { uicFcbAsn1Modules rtd(2) v3(3) 2 }

-- UIC Rail Ticket Data - version 3.0.3
uicRailTicketDataV3-0-3 OBJECT IDENTIFIER ::= { uicFcbAsn1Modules rtd(2) v3(3) 3 }

-- UIC Rail Ticket Data - version 3.0.4
uicRailTicketDataV3-0-4 OBJECT IDENTIFIER ::= { uicFcbAsn1Modules rtd(2) v3(3) 4 }

-- UIC Rail Ticket Data - version 3.0.5
uicRailTicketDataV3-0-5 OBJECT IDENTIFIER ::= { uicFcbAsn1Modules rtd(2) v3(3) 5 }

-- UIC Rail Ticket Data - version 3.0.6
uicRailTicketDataV3-0-6 OBJECT IDENTIFIER ::= { uicFcbAsn1Modules rtd(2) v3(3) 6 }

-- UIC Rail Ticket Data - version 3.0.7
uicRailTicketDataV3-0-7 OBJECT IDENTIFIER ::= { uicFcbAsn1Modules rtd(2) v3(3) 7 }

-- FCB Dynamic Content Data - version 1.0.0
uicDynamicContentDataV1-0-0 OBJECT IDENTIFIER ::= { uicFcbAsn1Modules dcd(3) v1(1) 0 }

-- FCB Dynamic Content Data - version 1.0.1
uicDynamicContentDataV1-0-1 OBJECT IDENTIFIER ::= { uicFcbAsn1Modules dcd(3) v1(1) 1 }

-- FCB Dynamic Content Data - version 1.0.2
uicDynamicContentDataV1-0-2 OBJECT IDENTIFIER ::= { uicFcbAsn1Modules dcd(3) v1(1) 2 }

-- FCB Dynamic Content Data - version 1.0.3
uicDynamicContentDataV1-0-3 OBJECT IDENTIFIER ::= { uicFcbAsn1Modules dcd(3) v1(1) 3 }

-- FCB Dynamic Content Data - version 1.0.4
uicDynamicContentDataV1-0-4 OBJECT IDENTIFIER ::= { uicFcbAsn1Modules dcd(3) v1(1) 4 }

-- FCB Dynamic Content Data - version 1.0.5
uicDynamicContentDataV1-0-5 OBJECT IDENTIFIER ::= { uicFcbAsn1Modules dcd(3) v1(1) 5 }

-- FCB Dynamic Content Data - version 2.0.0, currently a draft
uicDynamicContentDataV2-0-0 OBJECT IDENTIFIER ::= { uicFcbAsn1Modules dcd(3) v2(2) 0 }

-- UIC Multi-Modal Ticket Data - version 1.0.0, currently a draft
uicMultiModalTicketDataV1-0-0 OBJECT IDENTIFIER ::= { uicFcbAsn1Modules mmtd(4) v1(1) 0 }

-- UIC General cross-module data - version 1.0.0, currently a draft
uicGeneralDataV1-0-0 OBJECT IDENTIFIER ::= { uicFcbAsn1Modules general(5) v1(1) 0 }

-- UIC Fixed Point Data - version 1.0.0, currently a draft
uicFixedPointDataV1-0-0 OBJECT IDENTIFIER ::= { uicFcbAsn1Modules fpd(6) v1(1) 0 }

END
