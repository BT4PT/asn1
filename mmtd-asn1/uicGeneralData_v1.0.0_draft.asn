/**
* Generic definitions for common elements shared across many UIC ASN.1 modules. Version 1.0.0.
*
* ISO Country codes are used to code countries.
* As Kosovo does not have an official ISO Country Code the following codes are used:
* - `926` for Kosovo as numeric ISO Country Code
* - `XK` for Kosovo as alphanumeric 2-character ISO Country Code.
*/
GeneralData { iso(1) identified-organization(3) dod(6)
    internet(1) private(4) enterprise(1) uic(17218) fcb(1) modules(0) general(5) v1(1) 0 }
    DEFINITIONS AUTOMATIC TAGS ::= BEGIN

EXPORTS ALL;

/**
* Identification of any element using a numerical, alphanumerical or binary ID, according to the code list defined in the container object.
* Note, the choice of encoding variant has no differentiating effect on the value. That is, `1234` encoded as an `idNum` is the exact
* same logical value as the string `"1234"` encoded as `idIA5`, and the same logical value as the octal string `'31323334'H`.
*/
GenericId ::= CHOICE {
    idNum   INTEGER,        -- for numerical IDs
    idIA5   VisibleString,  -- for alphanumerical IDs
    idOct   OCTET STRING    -- for binary IDs such as UUIDs
}

CodeTable ::= SEQUENCE {
    owner CHOICE {
        /**
        * ID values defined by the document issuer.
        */
        issuer          NULL,
        /**
        * ID values defined by the product owner.
        */
        productOwner    NULL,
        /**
        * ID values defined by the carrier(s).
        */
        carrier         NULL,
        /**
        * ID values defined by the organisation responsible for the `concernedArea`.
        */
        area            NULL,
        /**
        * ID values defined by the national authority the country defined by its ISO 3166-1 numeric code.
        */
        national        INTEGER (0..999),
        /**
        * ID values defined by the referenced company.
        */
        company         CompanyCode
    },
    version INTEGER (0..255) DEFAULT 0
}

CODE-TABLE-IDENTIFIER ::= CLASS {
    &table CodeTable UNIQUE,
    &name UTF8String
} WITH SYNTAX {
    &table MEANING &name
}

GenericCode{IdType, CODE-TABLE-IDENTIFIER: TableSet} ::= SEQUENCE {
    codeTable CODE-TABLE-IDENTIFIER.&table({TableSet}),
    id IdType
}

/**
* A STOP PLACE in Transmodel (EN 12896-2:2016 § 5.4.3).
*/
Station ::= SEQUENCE {
    station             CHOICE {
        /**
        * ERA TEL TSI Primary Location Code, as per [teleref.era.europa.eu](https://teleref.era.europa.eu).
        * - A 7 digit code (country code + 5 digit local code) defines a rail station code.
        * - A 9 digit code (2-digit scope code + country code + 5 digit local code) defines a non-rail station code.
        */
        era         INTEGER (1..999999999),
        generic     GenericCode{GenericId, StationCodeTables}
    },
    stationNameUTF8     UnicodeText OPTIONAL
}

StationCodeTables CODE-TABLE-IDENTIFIER ::= {
    {{
        owner company : orgCode : "1170",
        version 0
    } MEANING "UK National Location Code"} | -- SHALL NOT be used except when an NLC contains letters, and thus can't be turned into an ERA PLC.
    {{
        owner national : 826,
        version 0
    } MEANING "UK NaPTAN Code"} |
    {{
        owner national : 276,
        version 0
    } MEANING "ZHV Deutschlandweite Haltestellen-ID"} | -- DHIDs are encoded without the `de:` prefix
    {{
        owner national : 756,
        version 0
    } MEANING "Swiss LOcation IDentification"}, -- Encoded without the `ch:1:sloid:` prefix,
    ...
}

StationSet ::= SEQUENCE {
    set CHOICE {
        /**
        * Where a station group is defined a number of stations grouped together with a primary station.
        */
        groupPrimary    Station,
        /**
        * Explicitly listing all stations in a group.
        */
        list            SEQUENCE OF Station
    },
    setNameUTF8 UnicodeText OPTIONAL
}

/**
* A LINE in Transmodel (EN 12896-2:2016 § 5.3.7.4).
*/
LineId ::= CHOICE {
    /**
    * e.g. "RE1".
    */
    publicIdentifier    VisibleString (FROM ("A".."Z"|"0".."9")),
    generic             GenericCode{GenericId, LineIdCodeTables}
}

LineIdCodeTables CODE-TABLE-IDENTIFIER ::= {
    {{
        owner national : 276,
        version 0
    } MEANING "VDV 431-2 Line ID"} | -- Line IDs are encoded without the `de:` prefix
    {{
        owner national : 756,
        version 0
    } MEANING "Swiss LiNe IDentification"}, -- Encoded without the `ch:1:slnid:` prefix,
    ...
}

/**
* A SERVICE JOURNEY in Transmodel (EN 12896-3:2016 § 5.3.2).
*/
TransportId ::= CHOICE {
    /**
    * e.g. "ICE107".
    */
    publicIdentifier    VisibleString (FROM ("A".."Z"|"0".."9")),
    generic             GenericCode{GenericId, TransportIdCodeTables}
}

TransportIdCodeTables CODE-TABLE-IDENTIFIER ::= {
    {{
        owner national : 276,
        version 0
    } MEANING "VDV 431-2 Journey ID"} | -- Journey IDs are encoded without the `de:` prefix
    {{
        owner company : orgCode : "1170",
        version 0
    } MEANING "RDG UID"} |
    {{
        owner national : 756,
        version 0
    } MEANING "Swiss JourneY IDentification"}, -- Encoded without the `ch:1:sjyid:` prefix,
    ...
}

/**
* A geographic area defined under the Nomenclature of Territorial Units for Statistics (Regulation EC 1059/2003).
* Divisions all the way down to the Local Administrative Unit are permitted.
* NUTS codes are only defined for members of the EU, the EFTA, and EU candidate countries.
* FAUs are permitted standalone, e.g. `DE025F` (Freiburg im Breisgau) is coded with the subdivision `025F`.
* LAUs must be appended to their NUTS3 code, e.g. `DE13308316011` for Emmendingen, Stadt is coded with the subdivision `13308316011`.
* For those countries outside the NUTS system:
* - the UK maintains a compatible system since Brexit called the International Territorial Level;
* - otherwise, use the the [OECD Territorial Region Codes](http://oe.cd/geostats).
* - if none of the above applies for a country, a choice of suitable system **MUST** be defined by UIC,
*    users **MUST NOT** define bilateral subdivisions.
*/
NUTSArea ::= SEQUENCE {
    /**
    * ISO 3166-1 numeric code.
    */
    country         INTEGER (0..999),
    subdivision     VisibleString (FROM ("A".."Z"|"1".."9")) OPTIONAL
}

/**
* One or more areas of geographic validity.
*/
AreaSet ::= CHOICE {
    /**
    * European NUTS code, or compatible.
    */
    nuts    SEQUENCE OF NUTSArea,
    generic GenericCode{CHOICE {
        /**
        * e.g. sequence of allowed area/zone numbers such as `{1,5,23}`.
        */
        idNum    SEQUENCE OF INTEGER,
        /**
        * e.g. areas/zones described with text such as `{"M","1-3"}`.
        */
        idIA5    SEQUENCE OF VisibleString,
        /**
        * e.g. sequence of Calypso NetworkIds such as `{'250901'H,'250072'H}`.
        */
        idOct    SEQUENCE OF OCTET STRING,
        /**
        * Recommended encoding: bit n (considering that bit 0 = right-most bit) encodes area/zone n+1, bit value 1 = area/zone is allowed, bit value 0 = area/zone is forbidden.
        * e.g. bitmap of allowed areas/zones such as `'10101110010'B` for areas/zones 2, 5, 6, 7, 9 and 11.
        */
        idBit    BIT STRING
    }, AreaCodeTables}
}

AreaCodeTables CODE-TABLE-IDENTIFIER ::= { ... }

/**
* Place data according to TEL TSI B.5.
* `placeString`: place number ranges in case of groups.
*/
CoachPlaces ::= SEQUENCE {
    coach               VisibleString               OPTIONAL,

    /**
    * Printable place string  (e.g. "15-18, 21, 22").
    */
    placeString         VisibleString               OPTIONAL,

    /**
    * Printable place description.
    */
    placeDescription    UnicodeText                 OPTIONAL,

    /**
    * Individual places.
    */
    placeNumber         SEQUENCE OF PlaceNumber     OPTIONAL,

    details             PlaceDetails            OPTIONAL
}

/**
* Identification of an individual place.
*/
PlaceNumber ::= CHOICE {
    placeNum      INTEGER (1..999),
    placeIA5      VisibleString
}

/**
* Compartment details according to TEL TSI B.5.
*/
PlaceDetails ::= SEQUENCE {
    /**
    * Per TEL TSI Code List B.5.51.1.
    */
    coachType       INTEGER (0..99),
    /**
    * Per TEL TSI Code List B.5.51.2.
    */
    compartmentType INTEGER (0..99),
    /**
    * Per TEL TSI Code List B.5.51.3.
    */
    specialOffers   INTEGER (0..99),
    description     UnicodeText     OPTIONAL
}

/**
* Text fields in this specification are `OCTET STRINGS`.
* The contents of these fields **MUST** be encoded according to the [Standard Compression Scheme for Unicode (SCSU)](https://www.unicode.org/reports/tr6/tr6-4.html).
* For encoders than only ever output US-ASCII and ISO 8859-1 (Latin-1) between `U+0020` and `U+00FF`, no special handling is required to generate SCSU data,
*  the Latin-1 encoding is already valid SCSU.
* All decoders **MUST** be able to handle the full SCSU specification on reading and parsing data.
* If you are unsure which implementation to use, the [International Components for Unicode](https://icu.unicode.org/)
*  is the recommended implementation of SCSU, although it is by no means required.
*
* Systems dealing with the contained data **MUST** be compliant to DIN 91379.
* That is, they can handle (store, transfer, recall, and represent) all characters as specified in DIN 91379 without error.
*
* All Unicode text, before being fed into the SCSU compressor, **MUST** be in Normalisation Form C.
*
* When comparing names with identity documents, or when a Latinized representation of a name is required,
*   the system **MUST** transliterate according to ICAO 9303 Part 3, specifically sections 4.6 and 6.
* The text stored in the ticket **SHOULD** be in its original script, with transliteration performed by the reading device.
* The reading device **SHOULD** show both the original script, and the Latinized form.
*
* The `language` field, if present, **MUST** be used to select to correct Latinization of Cyrillic characters.
* The relevant languages for special considerations in ICAO 9303 Latinization are:
* - `be`: Belarusian
* - `bg`: Bulgarian
* - `uk`: Ukrainian
* - `mk`: Macedonian
* - `sr`: Serbian
*
* The `language` field **MAY** also be used to influence other transliterations, e.g. the different handling of diaereses by language.
*/
UnicodeText ::= SEQUENCE {
    /**
    * SCSU encoding of the textual data.
    */
    text        OCTET STRING,
    /**
    * ISO 639-1 coding (lower case) of the text's language.
    */
    language    VisibleString (SIZE(2) ^ FROM ("a".."z"))   OPTIONAL
}

/**
* Generic types for geo coordinates.
*/
GeoCoordinate ::= SEQUENCE {
    position            GeoUnit,
    coordinateSystem    GeoCoordinateSystem   DEFAULT wgs84,
    /**
    * If omitted the accuracy is unknown.
    */
    accuracy            GeoUnitType           OPTIONAL
}

GeoCoordinateSystem ::= ENUMERATED {
    /**
    * WGS 84 standard system.
    */
    wgs84   (0),
    /**
    * (outdated) GRS 80 coordinate system.
    */
    grs80   (1)
}

GeoUnitType ::= ENUMERATED {
    /**
    * 1 / 10000 degree is approx. 11 meter on earth surface.
    */
    tenthMilliDegree    (0), --
    /**
    * Approx. 110 meter on earth surface.
    */
    milliDegree         (1),
    centiDegree         (2),
    deciDegree          (3)
}

GeoUnit ::= CHOICE {
  tenthMilliDegree SEQUENCE {
    longitude INTEGER (-1800000..1800000),
    latitude  INTEGER (-900000..900000)
  },
  milliDegree SEQUENCE {
    longitude INTEGER (-180000..180000),
    latitude  INTEGER (-90000..90000)
  },
  centiDegree SEQUENCE {
    longitude INTEGER (-18000..18000),
    latitude  INTEGER (-9000..9000)
  },
  deciDegree SEQUENCE {
    longitude INTEGER (-1800..1800),
    latitude  INTEGER (-900..900)
  }
}

/**
* Generic timestamp, expressed in UTC.
*/
Timestamp ::= SEQUENCE {
    year INTEGER (2016..2269),
    /**
    * The number of the day in the year (1st Jan = 1).
    */
    day INTEGER (1..366),
    /**
    * The number of minutes of the day from 0 = 00:00 to 1439 = 23:59.
    */
    time INTEGER (0..1439)
}

/**
* The OID assigned to identify the Canonical Unaligned Packed Encoding Rules, per ITU-T X.691.
*/
cuperEncoding OBJECT IDENTIFIER ::= {joint-iso-itu-t (2) asn1 (1) packed-encoding (3) canonical (1) unaligned (1)}

/**
* A TRANSPORT ORGANIZATION in Transmodel (EN 12896-1:2016 § 5.6.8).
*/
CompanyCode ::= CHOICE {
    /**
    * For companies within the EU this field **SHALL** be their ERA assigned Organisation Code.
    * For others this field **SHALL** be their UIC assed RICS Code.
    * If a company has no such code, otherCode **MAY** be used.
    * ERA Organisation Codes are available from [teleref.era.europa.eu](https://teleref.era.europa.eu)
    * UIC RICS Codes are available from [uic.org/support-activities/it/rics](https://uic.org/support-activities/it/rics).
    */
    orgCode     VisibleString (SIZE (4) ^ FROM ("A".."Z"|"0".."9")),

	otherCode   SEQUENCE {
	    /**
		* The value of `format` identifies the company identifier format according to the following:
		* - `+` + [2-letter uppercase ISO 3166 country code] + [addon, chosen by the national standards body of that country]
		* - `_` + [RICS or ERA Organisation Code] + [addon, chosen by this company]
		* - `*` + [addon] - private use, not guaranteed to avoid clashes
		*
        * Any other value only after registration in the appropriate registry.
        * Unregistered values (outside of the national, company, and private use ranges) **MUST NOT** be used.
        * If an organisation has a RICS or an ERA Organisation Code the private use format **MUST NOT** be used.
        * All values **SHOULD** be registered via the UIC Github repository.
		*/
		format      COMPANY-CODE-FORMAT.&id({CompanyCodeFormats}),
		code        VisibleString (SIZE(1..8,...))
	}
}

COMPANY-CODE-FORMAT ::= CLASS {
    &id VisibleString (SIZE(1..16) ^ (ALL EXCEPT ("!I" | "!C" | "!P"))) UNIQUE,
    &name UTF8String
} WITH SYNTAX {
    &id MEANING &name
}

CompanyCodeFormats COMPANY-CODE-FORMAT ::= {
    { "+DEVDV" MEANING "Verband Deutscher Verkehrsunternehmen Organisation ID" } |
    { "+GBNOC" MEANING "Traveline National Operator Code" } |
    { "+CHSBOID" MEANING "Swiss Business Organisation Identification" }, -- Encoded without the `ch:1:sboid:` prefix.
    ...
}


/**
* A data element, identified by its `&id`, containing data as specified by its `&Type`, and encoded into an `OCTET STRING`
* as specified by its `&encoding`.
* The identifier `&id` can be of the following forms:
* - `+` + [2-letters uppercase ISO 3166 country code] + [addon, chosen by the national standards body of that country]
* - `_` + [RICS or ERA Organisation Code] + [addon, chosen by this company]
* - `!I` + [addon, chosen by the issuer] - equivalent to the _RICS format, without repetition of the issuer's code.
* - `!C` + [addon, chosen by the carrier] - equivalent to the _RICS format, without repetition of the carriers's code.
* - `!P` + [addon, chosen by the product owner] - equivalent to the _RICS format, without repetition of the product owner's code.
* - `*` + [addon] - private use, not guaranteed to avoid clashes.
*
* Any other value only after registration in the appropriate registry.
* Unregistered values (outside of the national, company, and private use ranges) **MUST NOT** be used.
* If an organisation has a RICS or an ERA Organisation Code the private use format **MUST NOT** be used.
* If the `!C` form would be ambiguous (e.g. multiple carriers possible) it **MUST NOT** be used.
* All values **SHOULD** be registered via the UIC Github repository.
*/
DATA-ELEMENT ::= CLASS {
    &id VisibleString (SIZE(1..16)) UNIQUE,
    &Type,
    &encoding OBJECT IDENTIFIER
} WITH SYNTAX {
    &Type IDENTIFIED BY &id ENCODED WITH &encoding
}

/**
* Generic data container.
* @ElementSet Set of `DATA-ELEMENT` objects that are permitted as contents. This set **SHOULD** be extensible.
*/
Data{DATA-ELEMENT: ElementSet} ::= SEQUENCE {
    format DATA-ELEMENT.&id({ElementSet}),
    value OCTET STRING (CONTAINING DATA-ELEMENT.&Type({ElementSet}{@format}))
}

/**
* Per NeTEx PersonalVehicleCategory (CEN/TS 16614-5:2022 § 10.1.4.3.4.2).
*/
SharedVehicleVariety ::= ENUMERATED {
    /**
    * Scooter - small wheeled low mobile platform
    */
    scooter (0),
    /**
    * Bicycle.
    */
    bicycle (1),
    /**
    * Tricycle.
    */
    tricycle (2),
    /**
    * Tandem bicycle.
    */
    tandem (3),
    /**
    * Moped (Small motorbike).
    */
    moped (4),
    /**
    * Motorcycle.
    */
    motorcycle (5),
    /**
    * Motorcycle.
    */
    quadbike (6),
    /**
    * Car of any size.
    */
    car (7),
    /**
    * Extremely small vehicle.
    */
    microCar (8),
    /**
    * Very small vehicle.
    */
    miniCar (9),
    /**
    * Small vehicle.
    */
    smallCar (10),
    /**
    * Compact vehicle.
    */
    mediumCar (11),
    /**
    * Large vehicle.
    */
    largeCar (12),
    /**
    * Minivan.
    */
    minivan (13),
    /**
    * Large people transporter / minibus.
    */
    transporter (14),
    /**
    * Snowmobile.
    */
    snowmobile (15),
    /**
    * Other category.
    */
    other (16),
    ...
}

/**
* Per NeTEx PropulsionType (CEN/TS 16614-5:2022 § 10.1.4.3.2.2).
*/
SharedVehiclePropulsionType ::= ENUMERATED {
    /**
    * Combustion of any sort
    */
    combustion (0),
    /**
    * Electric/Combustion Hybrid
    */
    hybrid (1),
    /**
    * Human powered (pedal, scoot etc)
    */
    human (2),
    /**
    * Human power with electric assistance.
    */
    electricAssist (3),
    /**
    * Other power.
    */
    other (4),
    ...
}

/**
* As per GBFSv3.0, to be replaced by a NeTEx mapping once standardised.
*/
SharedVehicleReturnConstraint ::= ENUMERATED {
    freeFloating (0),
    roundtripStation (1),
    anyStation (2),
    hybrid (3),
    ...
}

END
